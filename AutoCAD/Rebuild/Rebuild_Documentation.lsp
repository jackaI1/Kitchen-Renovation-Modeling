(setvar "TILEMODE" 1)
(setvar "CMDECHO" 0)
(setvar "OSMODE" 0)
(setvar "DYNMODE" 0)
(setvar "INSUNITS" 1)
(setvar "MEASUREMENT" 0)
(setvar "LUNITS" 2)
(setvar "LUPREC" 4)
(setvar "FILEDIA" 0)
(setvar "GRIDMODE" 0)
(setvar "UCSICON" 0)
(command "_.UCS" "_W")
(command "_.PLAN" "_W")
(defun klay (n) (setvar "CLAYER" n))
(defun kbox (a b) (command "_.BOX" a (list (car b) (cadr b) (caddr a)) (- (caddr b) (caddr a))) (entlast))
(defun kname (e n) (entmod (append (entget e) (list (list -3 (list "KITCHEN" (cons 1000 n)))))))
(regapp "KITCHEN")
(if (not (tblsearch "LAYER" "F-CONTEXT")) (entmake (list '(0 . "LAYER") '(100 . "AcDbSymbolTableRecord") '(100 . "AcDbLayerTableRecord") (cons 2 "F-CONTEXT") '(70 . 0) (cons 62 8) '(6 . "Continuous") (cons 370 13))))
(if (not (tblsearch "LAYER" "A-WALL")) (entmake (list '(0 . "LAYER") '(100 . "AcDbSymbolTableRecord") '(100 . "AcDbLayerTableRecord") (cons 2 "A-WALL") '(70 . 0) (cons 62 8) '(6 . "Continuous") (cons 370 35))))
(if (not (tblsearch "LAYER" "A-FLOOR")) (entmake (list '(0 . "LAYER") '(100 . "AcDbSymbolTableRecord") '(100 . "AcDbLayerTableRecord") (cons 2 "A-FLOOR") '(70 . 0) (cons 62 8) '(6 . "Continuous") (cons 370 18))))
(if (not (tblsearch "LAYER" "A-CEILING")) (entmake (list '(0 . "LAYER") '(100 . "AcDbSymbolTableRecord") '(100 . "AcDbLayerTableRecord") (cons 2 "A-CEILING") '(70 . 0) (cons 62 8) '(6 . "Continuous") (cons 370 18))))
(if (not (tblsearch "LAYER" "A-JOINERY")) (entmake (list '(0 . "LAYER") '(100 . "AcDbSymbolTableRecord") '(100 . "AcDbLayerTableRecord") (cons 2 "A-JOINERY") '(70 . 0) (cons 62 7) '(6 . "Continuous") (cons 370 25))))
(if (not (tblsearch "LAYER" "A-GLASS")) (entmake (list '(0 . "LAYER") '(100 . "AcDbSymbolTableRecord") '(100 . "AcDbLayerTableRecord") (cons 2 "A-GLASS") '(70 . 0) (cons 62 4) '(6 . "Continuous") (cons 370 13))))
(if (not (tblsearch "LAYER" "C-CARCASS")) (entmake (list '(0 . "LAYER") '(100 . "AcDbSymbolTableRecord") '(100 . "AcDbLayerTableRecord") (cons 2 "C-CARCASS") '(70 . 0) (cons 62 32) '(6 . "Continuous") (cons 370 18))))
(if (not (tblsearch "LAYER" "C-FRONTS")) (entmake (list '(0 . "LAYER") '(100 . "AcDbSymbolTableRecord") '(100 . "AcDbLayerTableRecord") (cons 2 "C-FRONTS") '(70 . 0) (cons 62 33) '(6 . "Continuous") (cons 370 25))))
(if (not (tblsearch "LAYER" "C-PLINTH")) (entmake (list '(0 . "LAYER") '(100 . "AcDbSymbolTableRecord") '(100 . "AcDbLayerTableRecord") (cons 2 "C-PLINTH") '(70 . 0) (cons 62 8) '(6 . "Continuous") (cons 370 18))))
(if (not (tblsearch "LAYER" "C-HARDWARE")) (entmake (list '(0 . "LAYER") '(100 . "AcDbSymbolTableRecord") '(100 . "AcDbLayerTableRecord") (cons 2 "C-HARDWARE") '(70 . 0) (cons 62 9) '(6 . "Continuous") (cons 370 13))))
(if (not (tblsearch "LAYER" "C-GLASS")) (entmake (list '(0 . "LAYER") '(100 . "AcDbSymbolTableRecord") '(100 . "AcDbLayerTableRecord") (cons 2 "C-GLASS") '(70 . 0) (cons 62 4) '(6 . "Continuous") (cons 370 13))))
(if (not (tblsearch "LAYER" "S-PORCELAIN")) (entmake (list '(0 . "LAYER") '(100 . "AcDbSymbolTableRecord") '(100 . "AcDbLayerTableRecord") (cons 2 "S-PORCELAIN") '(70 . 0) (cons 62 7) '(6 . "Continuous") (cons 370 25))))
(if (not (tblsearch "LAYER" "M-METAL")) (entmake (list '(0 . "LAYER") '(100 . "AcDbSymbolTableRecord") '(100 . "AcDbLayerTableRecord") (cons 2 "M-METAL") '(70 . 0) (cons 62 9) '(6 . "Continuous") (cons 370 18))))
(if (not (tblsearch "LAYER" "M-GLASS")) (entmake (list '(0 . "LAYER") '(100 . "AcDbSymbolTableRecord") '(100 . "AcDbLayerTableRecord") (cons 2 "M-GLASS") '(70 . 0) (cons 62 250) '(6 . "Continuous") (cons 370 13))))
(if (not (tblsearch "LAYER" "M-DUCT")) (entmake (list '(0 . "LAYER") '(100 . "AcDbSymbolTableRecord") '(100 . "AcDbLayerTableRecord") (cons 2 "M-DUCT") '(70 . 0) (cons 62 8) '(6 . "Continuous") (cons 370 13))))
(if (not (tblsearch "LAYER" "E-LIGHT")) (entmake (list '(0 . "LAYER") '(100 . "AcDbSymbolTableRecord") '(100 . "AcDbLayerTableRecord") (cons 2 "E-LIGHT") '(70 . 0) (cons 62 2) '(6 . "Continuous") (cons 370 13))))
(if (not (tblsearch "LAYER" "D-OUTLINE")) (entmake (list '(0 . "LAYER") '(100 . "AcDbSymbolTableRecord") '(100 . "AcDbLayerTableRecord") (cons 2 "D-OUTLINE") '(70 . 0) (cons 62 7) '(6 . "Continuous") (cons 370 30))))
(if (not (tblsearch "LAYER" "D-WALL")) (entmake (list '(0 . "LAYER") '(100 . "AcDbSymbolTableRecord") '(100 . "AcDbLayerTableRecord") (cons 2 "D-WALL") '(70 . 0) (cons 62 7) '(6 . "Continuous") (cons 370 50))))
(if (not (tblsearch "LAYER" "D-HIDDEN")) (entmake (list '(0 . "LAYER") '(100 . "AcDbSymbolTableRecord") '(100 . "AcDbLayerTableRecord") (cons 2 "D-HIDDEN") '(70 . 0) (cons 62 8) '(6 . "Continuous") (cons 370 13))))
(if (not (tblsearch "LAYER" "D-FINE")) (entmake (list '(0 . "LAYER") '(100 . "AcDbSymbolTableRecord") '(100 . "AcDbLayerTableRecord") (cons 2 "D-FINE") '(70 . 0) (cons 62 8) '(6 . "Continuous") (cons 370 13))))
(if (not (tblsearch "LAYER" "D-DIMS")) (entmake (list '(0 . "LAYER") '(100 . "AcDbSymbolTableRecord") '(100 . "AcDbLayerTableRecord") (cons 2 "D-DIMS") '(70 . 0) (cons 62 7) '(6 . "Continuous") (cons 370 13))))
(if (not (tblsearch "LAYER" "D-TEXT")) (entmake (list '(0 . "LAYER") '(100 . "AcDbSymbolTableRecord") '(100 . "AcDbLayerTableRecord") (cons 2 "D-TEXT") '(70 . 0) (cons 62 7) '(6 . "Continuous") (cons 370 13))))
(if (not (tblsearch "LAYER" "D-TITLE")) (entmake (list '(0 . "LAYER") '(100 . "AcDbSymbolTableRecord") '(100 . "AcDbLayerTableRecord") (cons 2 "D-TITLE") '(70 . 0) (cons 62 7) '(6 . "Continuous") (cons 370 35))))
(if (not (tblsearch "LAYER" "D-HATCH")) (entmake (list '(0 . "LAYER") '(100 . "AcDbSymbolTableRecord") '(100 . "AcDbLayerTableRecord") (cons 2 "D-HATCH") '(70 . 0) (cons 62 8) '(6 . "Continuous") (cons 370 9))))
(if (not (tblsearch "LAYER" "D-HOLD")) (entmake (list '(0 . "LAYER") '(100 . "AcDbSymbolTableRecord") '(100 . "AcDbLayerTableRecord") (cons 2 "D-HOLD") '(70 . 0) (cons 62 7) '(6 . "Continuous") (cons 370 18))))
(if (not (tblsearch "LAYER" "VPORT")) (entmake (list '(0 . "LAYER") '(100 . "AcDbSymbolTableRecord") '(100 . "AcDbLayerTableRecord") (cons 2 "VPORT") '(70 . 0) (cons 62 8) '(6 . "Continuous") (cons 370 9))))

(setvar "TILEMODE" 1)
(command "_.VSCURRENT" "_2dwireframe")
(if (not (tblsearch "LTYPE" "HIDDEN")) (command "_.-LINETYPE" "_L" "HIDDEN" "acad.lin" ""))
(command "_.-LAYER" "_LT" "HIDDEN" "D-HIDDEN" "")
(setvar "LTSCALE" 12)
(setvar "PSLTSCALE" 0)

(command "_.ERASE" "_ALL" "")
(command "_.-STYLE" "KITCHEN" "Arial.ttf" 0 1 0 "_N" "_N")
(setvar "DIMLUNIT" 2) (setvar "DIMDEC" 4) (setvar "DIMRND" 0.0625) (setvar "DIMFRAC" 2)
(setvar "DIMDSEP" ".") (setvar "DIMZIN" 8) (setvar "DIMASSOC" 1) (setvar "DIMLFAC" 1.0)
(setvar "DIMSCALE" 1.0) (setvar "DIMTAD" 1) (setvar "DIMTIH" 0) (setvar "DIMTOH" 0)
(setvar "DIMCLRD" 0) (setvar "DIMCLRE" 0) (setvar "DIMCLRT" 0)
(setvar "DIMTXSTY" "KITCHEN")
(setvar "DIMTXT" 1.68) (setvar "DIMASZ" 1.2) (setvar "DIMGAP" 0.64) (setvar "DIMEXO" 0.96) (setvar "DIMEXE" 0.96)
(if (tblsearch "DIMSTYLE" "KITCHEN_1_16") (command "_.-DIMSTYLE" "_S" "KITCHEN_1_16" "_Y") (command "_.-DIMSTYLE" "_S" "KITCHEN_1_16"))
(command "_.-DIMSTYLE" "_R" "KITCHEN_1_16")
(klay "D-TITLE")
(command "_.RECTANG" '(6.400000 6.400000 0.000000) '(377.600000 281.600000 0.000000))
(klay "D-TITLE")
(entmake (list '(0 . "LINE") (cons 8 "D-TITLE") (cons 10 '(6.400000 27.200000 0.000000)) (cons 11 '(377.600000 27.200000 0.000000))))
(klay "D-TITLE")
(entmake (list '(0 . "TEXT") (cons 8 "D-TITLE") (cons 10 '(11.200000 12.800000 0.000000)) (cons 40 2.56) (cons 1 "KITCHEN RENOVATION") '(7 . "KITCHEN") '(50 . 0.0)))
(klay "D-TEXT")
(entmake (list '(0 . "TEXT") (cons 8 "D-TEXT") (cons 10 '(11.200000 8.800000 0.000000)) (cons 40 1.44) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(244.800000 17.920000 0.000000)) (cons 40 2.24) (cons 1 "Kitchen plan") '(7 . "KITCHEN") '(50 . 0.0)))
(klay "D-TEXT")
(entmake (list '(0 . "TEXT") (cons 8 "D-TEXT") (cons 10 '(244.800000 11.200000 0.000000)) (cons 40 1.52) (cons 1 "22 OCT 2026  |  3/4 in. = 1 ft  |  24 x 18 in.  |  INCHES") '(7 . "KITCHEN") '(50 . 0.0)))
(klay "D-TITLE")
(entmake (list '(0 . "TEXT") (cons 8 "D-TITLE") (cons 10 '(345.600000 12.000000 0.000000)) (cons 40 5.44) (cons 1 "A101") '(7 . "KITCHEN") '(50 . 0.0)))
(klay "D-TITLE")
(entmake (list '(0 . "TEXT") (cons 8 "D-TITLE") (cons 10 '(11.200000 274.400000 0.000000)) (cons 40 3.68) (cons 1 "KITCHEN PLAN") '(7 . "KITCHEN") '(50 . 0.0)))
(klay "D-TEXT")
(entmake (list '(0 . "TEXT") (cons 8 "D-TEXT") (cons 10 '(11.200000 269.760000 0.000000)) (cons 40 1.44) (cons 1 "SOURCE COORDINATION / 22 OCT 2026") '(7 . "KITCHEN") '(50 . 0.0)))
(klay "D-WALL")
(command "_.RECTANG" '(33.000000 240.000000 0.000000) '(206.000000 244.000000 0.000000))
(klay "D-WALL")
(command "_.RECTANG" '(33.000000 127.000000 0.000000) '(37.000000 240.000000 0.000000))
(klay "D-WALL")
(command "_.RECTANG" '(202.000000 206.750000 0.000000) '(206.000000 240.000000 0.000000))
(klay "D-WALL")
(command "_.RECTANG" '(202.000000 56.750000 0.000000) '(206.000000 154.750000 0.000000))
(klay "D-HATCH")
(entmake (list '(0 . "LINE") (cons 8 "D-HATCH") (cons 10 '(33.000000 243.000000 0.000000)) (cons 11 '(36.000000 240.000000 0.000000))))
(klay "D-HATCH")
(entmake (list '(0 . "LINE") (cons 8 "D-HATCH") (cons 10 '(35.000000 244.000000 0.000000)) (cons 11 '(39.000000 240.000000 0.000000))))
(klay "D-HATCH")
(entmake (list '(0 . "LINE") (cons 8 "D-HATCH") (cons 10 '(38.000000 244.000000 0.000000)) (cons 11 '(42.000000 240.000000 0.000000))))
(klay "D-HATCH")
(entmake (list '(0 . "LINE") (cons 8 "D-HATCH") (cons 10 '(41.000000 244.000000 0.000000)) (cons 11 '(45.000000 240.000000 0.000000))))
(klay "D-HATCH")
(entmake (list '(0 . "LINE") (cons 8 "D-HATCH") (cons 10 '(44.000000 244.000000 0.000000)) (cons 11 '(48.000000 240.000000 0.000000))))
(klay "D-HATCH")
(entmake (list '(0 . "LINE") (cons 8 "D-HATCH") (cons 10 '(47.000000 244.000000 0.000000)) (cons 11 '(51.000000 240.000000 0.000000))))
(klay "D-HATCH")
(entmake (list '(0 . "LINE") (cons 8 "D-HATCH") (cons 10 '(50.000000 244.000000 0.000000)) (cons 11 '(54.000000 240.000000 0.000000))))
(klay "D-HATCH")
(entmake (list '(0 . "LINE") (cons 8 "D-HATCH") (cons 10 '(53.000000 244.000000 0.000000)) (cons 11 '(57.000000 240.000000 0.000000))))
(klay "D-HATCH")
(entmake (list '(0 . "LINE") (cons 8 "D-HATCH") (cons 10 '(56.000000 244.000000 0.000000)) (cons 11 '(60.000000 240.000000 0.000000))))
(klay "D-HATCH")
(entmake (list '(0 . "LINE") (cons 8 "D-HATCH") (cons 10 '(59.000000 244.000000 0.000000)) (cons 11 '(63.000000 240.000000 0.000000))))
(klay "D-HATCH")
(entmake (list '(0 . "LINE") (cons 8 "D-HATCH") (cons 10 '(62.000000 244.000000 0.000000)) (cons 11 '(66.000000 240.000000 0.000000))))
(klay "D-HATCH")
(entmake (list '(0 . "LINE") (cons 8 "D-HATCH") (cons 10 '(65.000000 244.000000 0.000000)) (cons 11 '(69.000000 240.000000 0.000000))))
(klay "D-HATCH")
(entmake (list '(0 . "LINE") (cons 8 "D-HATCH") (cons 10 '(68.000000 244.000000 0.000000)) (cons 11 '(72.000000 240.000000 0.000000))))
(klay "D-HATCH")
(entmake (list '(0 . "LINE") (cons 8 "D-HATCH") (cons 10 '(71.000000 244.000000 0.000000)) (cons 11 '(75.000000 240.000000 0.000000))))
(klay "D-HATCH")
(entmake (list '(0 . "LINE") (cons 8 "D-HATCH") (cons 10 '(74.000000 244.000000 0.000000)) (cons 11 '(78.000000 240.000000 0.000000))))
(klay "D-HATCH")
(entmake (list '(0 . "LINE") (cons 8 "D-HATCH") (cons 10 '(77.000000 244.000000 0.000000)) (cons 11 '(81.000000 240.000000 0.000000))))
(klay "D-HATCH")
(entmake (list '(0 . "LINE") (cons 8 "D-HATCH") (cons 10 '(80.000000 244.000000 0.000000)) (cons 11 '(84.000000 240.000000 0.000000))))
(klay "D-HATCH")
(entmake (list '(0 . "LINE") (cons 8 "D-HATCH") (cons 10 '(83.000000 244.000000 0.000000)) (cons 11 '(87.000000 240.000000 0.000000))))
(klay "D-HATCH")
(entmake (list '(0 . "LINE") (cons 8 "D-HATCH") (cons 10 '(86.000000 244.000000 0.000000)) (cons 11 '(90.000000 240.000000 0.000000))))
(klay "D-HATCH")
(entmake (list '(0 . "LINE") (cons 8 "D-HATCH") (cons 10 '(89.000000 244.000000 0.000000)) (cons 11 '(93.000000 240.000000 0.000000))))
(klay "D-HATCH")
(entmake (list '(0 . "LINE") (cons 8 "D-HATCH") (cons 10 '(92.000000 244.000000 0.000000)) (cons 11 '(96.000000 240.000000 0.000000))))
(klay "D-HATCH")
(entmake (list '(0 . "LINE") (cons 8 "D-HATCH") (cons 10 '(95.000000 244.000000 0.000000)) (cons 11 '(99.000000 240.000000 0.000000))))
(klay "D-HATCH")
(entmake (list '(0 . "LINE") (cons 8 "D-HATCH") (cons 10 '(98.000000 244.000000 0.000000)) (cons 11 '(102.000000 240.000000 0.000000))))
(klay "D-HATCH")
(entmake (list '(0 . "LINE") (cons 8 "D-HATCH") (cons 10 '(101.000000 244.000000 0.000000)) (cons 11 '(105.000000 240.000000 0.000000))))
(klay "D-HATCH")
(entmake (list '(0 . "LINE") (cons 8 "D-HATCH") (cons 10 '(104.000000 244.000000 0.000000)) (cons 11 '(108.000000 240.000000 0.000000))))
(klay "D-HATCH")
(entmake (list '(0 . "LINE") (cons 8 "D-HATCH") (cons 10 '(107.000000 244.000000 0.000000)) (cons 11 '(111.000000 240.000000 0.000000))))
(klay "D-HATCH")
(entmake (list '(0 . "LINE") (cons 8 "D-HATCH") (cons 10 '(110.000000 244.000000 0.000000)) (cons 11 '(114.000000 240.000000 0.000000))))
(klay "D-HATCH")
(entmake (list '(0 . "LINE") (cons 8 "D-HATCH") (cons 10 '(113.000000 244.000000 0.000000)) (cons 11 '(117.000000 240.000000 0.000000))))
(klay "D-HATCH")
(entmake (list '(0 . "LINE") (cons 8 "D-HATCH") (cons 10 '(116.000000 244.000000 0.000000)) (cons 11 '(120.000000 240.000000 0.000000))))
(klay "D-HATCH")
(entmake (list '(0 . "LINE") (cons 8 "D-HATCH") (cons 10 '(119.000000 244.000000 0.000000)) (cons 11 '(123.000000 240.000000 0.000000))))
(klay "D-HATCH")
(entmake (list '(0 . "LINE") (cons 8 "D-HATCH") (cons 10 '(122.000000 244.000000 0.000000)) (cons 11 '(126.000000 240.000000 0.000000))))
(klay "D-HATCH")
(entmake (list '(0 . "LINE") (cons 8 "D-HATCH") (cons 10 '(125.000000 244.000000 0.000000)) (cons 11 '(129.000000 240.000000 0.000000))))
(klay "D-HATCH")
(entmake (list '(0 . "LINE") (cons 8 "D-HATCH") (cons 10 '(128.000000 244.000000 0.000000)) (cons 11 '(132.000000 240.000000 0.000000))))
(klay "D-HATCH")
(entmake (list '(0 . "LINE") (cons 8 "D-HATCH") (cons 10 '(131.000000 244.000000 0.000000)) (cons 11 '(135.000000 240.000000 0.000000))))
(klay "D-HATCH")
(entmake (list '(0 . "LINE") (cons 8 "D-HATCH") (cons 10 '(134.000000 244.000000 0.000000)) (cons 11 '(138.000000 240.000000 0.000000))))
(klay "D-HATCH")
(entmake (list '(0 . "LINE") (cons 8 "D-HATCH") (cons 10 '(137.000000 244.000000 0.000000)) (cons 11 '(141.000000 240.000000 0.000000))))
(klay "D-HATCH")
(entmake (list '(0 . "LINE") (cons 8 "D-HATCH") (cons 10 '(140.000000 244.000000 0.000000)) (cons 11 '(144.000000 240.000000 0.000000))))
(klay "D-HATCH")
(entmake (list '(0 . "LINE") (cons 8 "D-HATCH") (cons 10 '(143.000000 244.000000 0.000000)) (cons 11 '(147.000000 240.000000 0.000000))))
(klay "D-HATCH")
(entmake (list '(0 . "LINE") (cons 8 "D-HATCH") (cons 10 '(146.000000 244.000000 0.000000)) (cons 11 '(150.000000 240.000000 0.000000))))
(klay "D-HATCH")
(entmake (list '(0 . "LINE") (cons 8 "D-HATCH") (cons 10 '(149.000000 244.000000 0.000000)) (cons 11 '(153.000000 240.000000 0.000000))))
(klay "D-HATCH")
(entmake (list '(0 . "LINE") (cons 8 "D-HATCH") (cons 10 '(152.000000 244.000000 0.000000)) (cons 11 '(156.000000 240.000000 0.000000))))
(klay "D-HATCH")
(entmake (list '(0 . "LINE") (cons 8 "D-HATCH") (cons 10 '(155.000000 244.000000 0.000000)) (cons 11 '(159.000000 240.000000 0.000000))))
(klay "D-HATCH")
(entmake (list '(0 . "LINE") (cons 8 "D-HATCH") (cons 10 '(158.000000 244.000000 0.000000)) (cons 11 '(162.000000 240.000000 0.000000))))
(klay "D-HATCH")
(entmake (list '(0 . "LINE") (cons 8 "D-HATCH") (cons 10 '(161.000000 244.000000 0.000000)) (cons 11 '(165.000000 240.000000 0.000000))))
(klay "D-HATCH")
(entmake (list '(0 . "LINE") (cons 8 "D-HATCH") (cons 10 '(164.000000 244.000000 0.000000)) (cons 11 '(168.000000 240.000000 0.000000))))
(klay "D-HATCH")
(entmake (list '(0 . "LINE") (cons 8 "D-HATCH") (cons 10 '(167.000000 244.000000 0.000000)) (cons 11 '(171.000000 240.000000 0.000000))))
(klay "D-HATCH")
(entmake (list '(0 . "LINE") (cons 8 "D-HATCH") (cons 10 '(170.000000 244.000000 0.000000)) (cons 11 '(174.000000 240.000000 0.000000))))
(klay "D-HATCH")
(entmake (list '(0 . "LINE") (cons 8 "D-HATCH") (cons 10 '(173.000000 244.000000 0.000000)) (cons 11 '(177.000000 240.000000 0.000000))))
(klay "D-HATCH")
(entmake (list '(0 . "LINE") (cons 8 "D-HATCH") (cons 10 '(176.000000 244.000000 0.000000)) (cons 11 '(180.000000 240.000000 0.000000))))
(klay "D-HATCH")
(entmake (list '(0 . "LINE") (cons 8 "D-HATCH") (cons 10 '(179.000000 244.000000 0.000000)) (cons 11 '(183.000000 240.000000 0.000000))))
(klay "D-HATCH")
(entmake (list '(0 . "LINE") (cons 8 "D-HATCH") (cons 10 '(182.000000 244.000000 0.000000)) (cons 11 '(186.000000 240.000000 0.000000))))
(klay "D-HATCH")
(entmake (list '(0 . "LINE") (cons 8 "D-HATCH") (cons 10 '(185.000000 244.000000 0.000000)) (cons 11 '(189.000000 240.000000 0.000000))))
(klay "D-HATCH")
(entmake (list '(0 . "LINE") (cons 8 "D-HATCH") (cons 10 '(188.000000 244.000000 0.000000)) (cons 11 '(192.000000 240.000000 0.000000))))
(klay "D-HATCH")
(entmake (list '(0 . "LINE") (cons 8 "D-HATCH") (cons 10 '(191.000000 244.000000 0.000000)) (cons 11 '(195.000000 240.000000 0.000000))))
(klay "D-HATCH")
(entmake (list '(0 . "LINE") (cons 8 "D-HATCH") (cons 10 '(194.000000 244.000000 0.000000)) (cons 11 '(198.000000 240.000000 0.000000))))
(klay "D-HATCH")
(entmake (list '(0 . "LINE") (cons 8 "D-HATCH") (cons 10 '(197.000000 244.000000 0.000000)) (cons 11 '(201.000000 240.000000 0.000000))))
(klay "D-HATCH")
(entmake (list '(0 . "LINE") (cons 8 "D-HATCH") (cons 10 '(200.000000 244.000000 0.000000)) (cons 11 '(204.000000 240.000000 0.000000))))
(klay "D-HATCH")
(entmake (list '(0 . "LINE") (cons 8 "D-HATCH") (cons 10 '(203.000000 244.000000 0.000000)) (cons 11 '(206.000000 241.000000 0.000000))))
(klay "D-HATCH")
(entmake (list '(0 . "LINE") (cons 8 "D-HATCH") (cons 10 '(33.000000 130.000000 0.000000)) (cons 11 '(36.000000 127.000000 0.000000))))
(klay "D-HATCH")
(entmake (list '(0 . "LINE") (cons 8 "D-HATCH") (cons 10 '(33.000000 133.000000 0.000000)) (cons 11 '(37.000000 129.000000 0.000000))))
(klay "D-HATCH")
(entmake (list '(0 . "LINE") (cons 8 "D-HATCH") (cons 10 '(33.000000 136.000000 0.000000)) (cons 11 '(37.000000 132.000000 0.000000))))
(klay "D-HATCH")
(entmake (list '(0 . "LINE") (cons 8 "D-HATCH") (cons 10 '(33.000000 139.000000 0.000000)) (cons 11 '(37.000000 135.000000 0.000000))))
(klay "D-HATCH")
(entmake (list '(0 . "LINE") (cons 8 "D-HATCH") (cons 10 '(33.000000 142.000000 0.000000)) (cons 11 '(37.000000 138.000000 0.000000))))
(klay "D-HATCH")
(entmake (list '(0 . "LINE") (cons 8 "D-HATCH") (cons 10 '(33.000000 145.000000 0.000000)) (cons 11 '(37.000000 141.000000 0.000000))))
(klay "D-HATCH")
(entmake (list '(0 . "LINE") (cons 8 "D-HATCH") (cons 10 '(33.000000 148.000000 0.000000)) (cons 11 '(37.000000 144.000000 0.000000))))
(klay "D-HATCH")
(entmake (list '(0 . "LINE") (cons 8 "D-HATCH") (cons 10 '(33.000000 151.000000 0.000000)) (cons 11 '(37.000000 147.000000 0.000000))))
(klay "D-HATCH")
(entmake (list '(0 . "LINE") (cons 8 "D-HATCH") (cons 10 '(33.000000 154.000000 0.000000)) (cons 11 '(37.000000 150.000000 0.000000))))
(klay "D-HATCH")
(entmake (list '(0 . "LINE") (cons 8 "D-HATCH") (cons 10 '(33.000000 157.000000 0.000000)) (cons 11 '(37.000000 153.000000 0.000000))))
(klay "D-HATCH")
(entmake (list '(0 . "LINE") (cons 8 "D-HATCH") (cons 10 '(33.000000 160.000000 0.000000)) (cons 11 '(37.000000 156.000000 0.000000))))
(klay "D-HATCH")
(entmake (list '(0 . "LINE") (cons 8 "D-HATCH") (cons 10 '(33.000000 163.000000 0.000000)) (cons 11 '(37.000000 159.000000 0.000000))))
(klay "D-HATCH")
(entmake (list '(0 . "LINE") (cons 8 "D-HATCH") (cons 10 '(33.000000 166.000000 0.000000)) (cons 11 '(37.000000 162.000000 0.000000))))
(klay "D-HATCH")
(entmake (list '(0 . "LINE") (cons 8 "D-HATCH") (cons 10 '(33.000000 169.000000 0.000000)) (cons 11 '(37.000000 165.000000 0.000000))))
(klay "D-HATCH")
(entmake (list '(0 . "LINE") (cons 8 "D-HATCH") (cons 10 '(33.000000 172.000000 0.000000)) (cons 11 '(37.000000 168.000000 0.000000))))
(klay "D-HATCH")
(entmake (list '(0 . "LINE") (cons 8 "D-HATCH") (cons 10 '(33.000000 175.000000 0.000000)) (cons 11 '(37.000000 171.000000 0.000000))))
(klay "D-HATCH")
(entmake (list '(0 . "LINE") (cons 8 "D-HATCH") (cons 10 '(33.000000 178.000000 0.000000)) (cons 11 '(37.000000 174.000000 0.000000))))
(klay "D-HATCH")
(entmake (list '(0 . "LINE") (cons 8 "D-HATCH") (cons 10 '(33.000000 181.000000 0.000000)) (cons 11 '(37.000000 177.000000 0.000000))))
(klay "D-HATCH")
(entmake (list '(0 . "LINE") (cons 8 "D-HATCH") (cons 10 '(33.000000 184.000000 0.000000)) (cons 11 '(37.000000 180.000000 0.000000))))
(klay "D-HATCH")
(entmake (list '(0 . "LINE") (cons 8 "D-HATCH") (cons 10 '(33.000000 187.000000 0.000000)) (cons 11 '(37.000000 183.000000 0.000000))))
(klay "D-HATCH")
(entmake (list '(0 . "LINE") (cons 8 "D-HATCH") (cons 10 '(33.000000 190.000000 0.000000)) (cons 11 '(37.000000 186.000000 0.000000))))
(klay "D-HATCH")
(entmake (list '(0 . "LINE") (cons 8 "D-HATCH") (cons 10 '(33.000000 193.000000 0.000000)) (cons 11 '(37.000000 189.000000 0.000000))))
(klay "D-HATCH")
(entmake (list '(0 . "LINE") (cons 8 "D-HATCH") (cons 10 '(33.000000 196.000000 0.000000)) (cons 11 '(37.000000 192.000000 0.000000))))
(klay "D-HATCH")
(entmake (list '(0 . "LINE") (cons 8 "D-HATCH") (cons 10 '(33.000000 199.000000 0.000000)) (cons 11 '(37.000000 195.000000 0.000000))))
(klay "D-HATCH")
(entmake (list '(0 . "LINE") (cons 8 "D-HATCH") (cons 10 '(33.000000 202.000000 0.000000)) (cons 11 '(37.000000 198.000000 0.000000))))
(klay "D-HATCH")
(entmake (list '(0 . "LINE") (cons 8 "D-HATCH") (cons 10 '(33.000000 205.000000 0.000000)) (cons 11 '(37.000000 201.000000 0.000000))))
(klay "D-HATCH")
(entmake (list '(0 . "LINE") (cons 8 "D-HATCH") (cons 10 '(33.000000 208.000000 0.000000)) (cons 11 '(37.000000 204.000000 0.000000))))
(klay "D-HATCH")
(entmake (list '(0 . "LINE") (cons 8 "D-HATCH") (cons 10 '(33.000000 211.000000 0.000000)) (cons 11 '(37.000000 207.000000 0.000000))))
(klay "D-HATCH")
(entmake (list '(0 . "LINE") (cons 8 "D-HATCH") (cons 10 '(33.000000 214.000000 0.000000)) (cons 11 '(37.000000 210.000000 0.000000))))
(klay "D-HATCH")
(entmake (list '(0 . "LINE") (cons 8 "D-HATCH") (cons 10 '(33.000000 217.000000 0.000000)) (cons 11 '(37.000000 213.000000 0.000000))))
(klay "D-HATCH")
(entmake (list '(0 . "LINE") (cons 8 "D-HATCH") (cons 10 '(33.000000 220.000000 0.000000)) (cons 11 '(37.000000 216.000000 0.000000))))
(klay "D-HATCH")
(entmake (list '(0 . "LINE") (cons 8 "D-HATCH") (cons 10 '(33.000000 223.000000 0.000000)) (cons 11 '(37.000000 219.000000 0.000000))))
(klay "D-HATCH")
(entmake (list '(0 . "LINE") (cons 8 "D-HATCH") (cons 10 '(33.000000 226.000000 0.000000)) (cons 11 '(37.000000 222.000000 0.000000))))
(klay "D-HATCH")
(entmake (list '(0 . "LINE") (cons 8 "D-HATCH") (cons 10 '(33.000000 229.000000 0.000000)) (cons 11 '(37.000000 225.000000 0.000000))))
(klay "D-HATCH")
(entmake (list '(0 . "LINE") (cons 8 "D-HATCH") (cons 10 '(33.000000 232.000000 0.000000)) (cons 11 '(37.000000 228.000000 0.000000))))
(klay "D-HATCH")
(entmake (list '(0 . "LINE") (cons 8 "D-HATCH") (cons 10 '(33.000000 235.000000 0.000000)) (cons 11 '(37.000000 231.000000 0.000000))))
(klay "D-HATCH")
(entmake (list '(0 . "LINE") (cons 8 "D-HATCH") (cons 10 '(33.000000 238.000000 0.000000)) (cons 11 '(37.000000 234.000000 0.000000))))
(klay "D-HATCH")
(entmake (list '(0 . "LINE") (cons 8 "D-HATCH") (cons 10 '(34.000000 240.000000 0.000000)) (cons 11 '(37.000000 237.000000 0.000000))))
(klay "D-HATCH")
(entmake (list '(0 . "LINE") (cons 8 "D-HATCH") (cons 10 '(202.000000 209.750000 0.000000)) (cons 11 '(205.000000 206.750000 0.000000))))
(klay "D-HATCH")
(entmake (list '(0 . "LINE") (cons 8 "D-HATCH") (cons 10 '(202.000000 212.750000 0.000000)) (cons 11 '(206.000000 208.750000 0.000000))))
(klay "D-HATCH")
(entmake (list '(0 . "LINE") (cons 8 "D-HATCH") (cons 10 '(202.000000 215.750000 0.000000)) (cons 11 '(206.000000 211.750000 0.000000))))
(klay "D-HATCH")
(entmake (list '(0 . "LINE") (cons 8 "D-HATCH") (cons 10 '(202.000000 218.750000 0.000000)) (cons 11 '(206.000000 214.750000 0.000000))))
(klay "D-HATCH")
(entmake (list '(0 . "LINE") (cons 8 "D-HATCH") (cons 10 '(202.000000 221.750000 0.000000)) (cons 11 '(206.000000 217.750000 0.000000))))
(klay "D-HATCH")
(entmake (list '(0 . "LINE") (cons 8 "D-HATCH") (cons 10 '(202.000000 224.750000 0.000000)) (cons 11 '(206.000000 220.750000 0.000000))))
(klay "D-HATCH")
(entmake (list '(0 . "LINE") (cons 8 "D-HATCH") (cons 10 '(202.000000 227.750000 0.000000)) (cons 11 '(206.000000 223.750000 0.000000))))
(klay "D-HATCH")
(entmake (list '(0 . "LINE") (cons 8 "D-HATCH") (cons 10 '(202.000000 230.750000 0.000000)) (cons 11 '(206.000000 226.750000 0.000000))))
(klay "D-HATCH")
(entmake (list '(0 . "LINE") (cons 8 "D-HATCH") (cons 10 '(202.000000 233.750000 0.000000)) (cons 11 '(206.000000 229.750000 0.000000))))
(klay "D-HATCH")
(entmake (list '(0 . "LINE") (cons 8 "D-HATCH") (cons 10 '(202.000000 236.750000 0.000000)) (cons 11 '(206.000000 232.750000 0.000000))))
(klay "D-HATCH")
(entmake (list '(0 . "LINE") (cons 8 "D-HATCH") (cons 10 '(202.000000 239.750000 0.000000)) (cons 11 '(206.000000 235.750000 0.000000))))
(klay "D-HATCH")
(entmake (list '(0 . "LINE") (cons 8 "D-HATCH") (cons 10 '(204.750000 240.000000 0.000000)) (cons 11 '(206.000000 238.750000 0.000000))))
(klay "D-HATCH")
(entmake (list '(0 . "LINE") (cons 8 "D-HATCH") (cons 10 '(202.000000 59.750000 0.000000)) (cons 11 '(205.000000 56.750000 0.000000))))
(klay "D-HATCH")
(entmake (list '(0 . "LINE") (cons 8 "D-HATCH") (cons 10 '(202.000000 62.750000 0.000000)) (cons 11 '(206.000000 58.750000 0.000000))))
(klay "D-HATCH")
(entmake (list '(0 . "LINE") (cons 8 "D-HATCH") (cons 10 '(202.000000 65.750000 0.000000)) (cons 11 '(206.000000 61.750000 0.000000))))
(klay "D-HATCH")
(entmake (list '(0 . "LINE") (cons 8 "D-HATCH") (cons 10 '(202.000000 68.750000 0.000000)) (cons 11 '(206.000000 64.750000 0.000000))))
(klay "D-HATCH")
(entmake (list '(0 . "LINE") (cons 8 "D-HATCH") (cons 10 '(202.000000 71.750000 0.000000)) (cons 11 '(206.000000 67.750000 0.000000))))
(klay "D-HATCH")
(entmake (list '(0 . "LINE") (cons 8 "D-HATCH") (cons 10 '(202.000000 74.750000 0.000000)) (cons 11 '(206.000000 70.750000 0.000000))))
(klay "D-HATCH")
(entmake (list '(0 . "LINE") (cons 8 "D-HATCH") (cons 10 '(202.000000 77.750000 0.000000)) (cons 11 '(206.000000 73.750000 0.000000))))
(klay "D-HATCH")
(entmake (list '(0 . "LINE") (cons 8 "D-HATCH") (cons 10 '(202.000000 80.750000 0.000000)) (cons 11 '(206.000000 76.750000 0.000000))))
(klay "D-HATCH")
(entmake (list '(0 . "LINE") (cons 8 "D-HATCH") (cons 10 '(202.000000 83.750000 0.000000)) (cons 11 '(206.000000 79.750000 0.000000))))
(klay "D-HATCH")
(entmake (list '(0 . "LINE") (cons 8 "D-HATCH") (cons 10 '(202.000000 86.750000 0.000000)) (cons 11 '(206.000000 82.750000 0.000000))))
(klay "D-HATCH")
(entmake (list '(0 . "LINE") (cons 8 "D-HATCH") (cons 10 '(202.000000 89.750000 0.000000)) (cons 11 '(206.000000 85.750000 0.000000))))
(klay "D-HATCH")
(entmake (list '(0 . "LINE") (cons 8 "D-HATCH") (cons 10 '(202.000000 92.750000 0.000000)) (cons 11 '(206.000000 88.750000 0.000000))))
(klay "D-HATCH")
(entmake (list '(0 . "LINE") (cons 8 "D-HATCH") (cons 10 '(202.000000 95.750000 0.000000)) (cons 11 '(206.000000 91.750000 0.000000))))
(klay "D-HATCH")
(entmake (list '(0 . "LINE") (cons 8 "D-HATCH") (cons 10 '(202.000000 98.750000 0.000000)) (cons 11 '(206.000000 94.750000 0.000000))))
(klay "D-HATCH")
(entmake (list '(0 . "LINE") (cons 8 "D-HATCH") (cons 10 '(202.000000 101.750000 0.000000)) (cons 11 '(206.000000 97.750000 0.000000))))
(klay "D-HATCH")
(entmake (list '(0 . "LINE") (cons 8 "D-HATCH") (cons 10 '(202.000000 104.750000 0.000000)) (cons 11 '(206.000000 100.750000 0.000000))))
(klay "D-HATCH")
(entmake (list '(0 . "LINE") (cons 8 "D-HATCH") (cons 10 '(202.000000 107.750000 0.000000)) (cons 11 '(206.000000 103.750000 0.000000))))
(klay "D-HATCH")
(entmake (list '(0 . "LINE") (cons 8 "D-HATCH") (cons 10 '(202.000000 110.750000 0.000000)) (cons 11 '(206.000000 106.750000 0.000000))))
(klay "D-HATCH")
(entmake (list '(0 . "LINE") (cons 8 "D-HATCH") (cons 10 '(202.000000 113.750000 0.000000)) (cons 11 '(206.000000 109.750000 0.000000))))
(klay "D-HATCH")
(entmake (list '(0 . "LINE") (cons 8 "D-HATCH") (cons 10 '(202.000000 116.750000 0.000000)) (cons 11 '(206.000000 112.750000 0.000000))))
(klay "D-HATCH")
(entmake (list '(0 . "LINE") (cons 8 "D-HATCH") (cons 10 '(202.000000 119.750000 0.000000)) (cons 11 '(206.000000 115.750000 0.000000))))
(klay "D-HATCH")
(entmake (list '(0 . "LINE") (cons 8 "D-HATCH") (cons 10 '(202.000000 122.750000 0.000000)) (cons 11 '(206.000000 118.750000 0.000000))))
(klay "D-HATCH")
(entmake (list '(0 . "LINE") (cons 8 "D-HATCH") (cons 10 '(202.000000 125.750000 0.000000)) (cons 11 '(206.000000 121.750000 0.000000))))
(klay "D-HATCH")
(entmake (list '(0 . "LINE") (cons 8 "D-HATCH") (cons 10 '(202.000000 128.750000 0.000000)) (cons 11 '(206.000000 124.750000 0.000000))))
(klay "D-HATCH")
(entmake (list '(0 . "LINE") (cons 8 "D-HATCH") (cons 10 '(202.000000 131.750000 0.000000)) (cons 11 '(206.000000 127.750000 0.000000))))
(klay "D-HATCH")
(entmake (list '(0 . "LINE") (cons 8 "D-HATCH") (cons 10 '(202.000000 134.750000 0.000000)) (cons 11 '(206.000000 130.750000 0.000000))))
(klay "D-HATCH")
(entmake (list '(0 . "LINE") (cons 8 "D-HATCH") (cons 10 '(202.000000 137.750000 0.000000)) (cons 11 '(206.000000 133.750000 0.000000))))
(klay "D-HATCH")
(entmake (list '(0 . "LINE") (cons 8 "D-HATCH") (cons 10 '(202.000000 140.750000 0.000000)) (cons 11 '(206.000000 136.750000 0.000000))))
(klay "D-HATCH")
(entmake (list '(0 . "LINE") (cons 8 "D-HATCH") (cons 10 '(202.000000 143.750000 0.000000)) (cons 11 '(206.000000 139.750000 0.000000))))
(klay "D-HATCH")
(entmake (list '(0 . "LINE") (cons 8 "D-HATCH") (cons 10 '(202.000000 146.750000 0.000000)) (cons 11 '(206.000000 142.750000 0.000000))))
(klay "D-HATCH")
(entmake (list '(0 . "LINE") (cons 8 "D-HATCH") (cons 10 '(202.000000 149.750000 0.000000)) (cons 11 '(206.000000 145.750000 0.000000))))
(klay "D-HATCH")
(entmake (list '(0 . "LINE") (cons 8 "D-HATCH") (cons 10 '(202.000000 152.750000 0.000000)) (cons 11 '(206.000000 148.750000 0.000000))))
(klay "D-HATCH")
(entmake (list '(0 . "LINE") (cons 8 "D-HATCH") (cons 10 '(203.000000 154.750000 0.000000)) (cons 11 '(206.000000 151.750000 0.000000))))
(klay "D-OUTLINE")
(command "_.RECTANG" '(37.000000 214.000000 0.000000) '(105.250000 240.000000 0.000000))
(klay "D-OUTLINE")
(command "_.RECTANG" '(37.000000 204.750000 0.000000) '(63.000000 214.000000 0.000000))
(klay "D-OUTLINE")
(command "_.RECTANG" '(135.750000 214.000000 0.000000) '(202.000000 240.000000 0.000000))
(klay "D-OUTLINE")
(command "_.RECTANG" '(176.000000 76.500000 0.000000) '(202.000000 214.000000 0.000000))
(klay "D-OUTLINE")
(command "_.RECTANG" '(104.500000 102.000000 0.000000) '(136.500000 168.000000 0.000000))
(klay "D-OUTLINE")
(entmake (list '(0 . "LINE") (cons 8 "D-OUTLINE") (cons 10 '(176.000000 198.000000 0.000000)) (cons 11 '(202.000000 198.000000 0.000000))))
(klay "D-TEXT")
(entmake (list '(0 . "TEXT") (cons 8 "D-TEXT") (cons 10 '(207.000000 197.000000 0.000000)) (cons 40 1.68) (cons 1 "J-C / J-B") '(7 . "KITCHEN") '(50 . 0.0)))
(klay "D-FINE")
(command "_.RECTANG" '(179.500000 166.250000 0.000000) '(197.500000 195.250000 0.000000))
(klay "D-FINE")
(entmake (list '(0 . "CIRCLE") (cons 8 "D-FINE") (cons 10 '(193.250000 190.750000 0.000000)) (cons 40 1.82)))
(klay "D-FINE")
(entmake (list '(0 . "CIRCLE") (cons 8 "D-FINE") (cons 10 '(199.000000 180.750000 0.000000)) (cons 40 0.7)))
(klay "D-FINE")
(entmake (list '(0 . "CIRCLE") (cons 8 "D-FINE") (cons 10 '(198.200000 161.750000 0.000000)) (cons 40 0.7)))
(klay "D-FINE")
(entmake (list '(0 . "LINE") (cons 8 "D-FINE") (cons 10 '(72.250000 240.000000 0.000000)) (cons 11 '(72.250000 214.500000 0.000000))))
(klay "D-FINE")
(entmake (list '(0 . "LINE") (cons 8 "D-FINE") (cons 10 '(95.250000 240.000000 0.000000)) (cons 11 '(95.250000 214.500000 0.000000))))
(klay "D-FINE")
(entmake (list '(0 . "LINE") (cons 8 "D-FINE") (cons 10 '(105.250000 240.000000 0.000000)) (cons 11 '(105.250000 214.500000 0.000000))))
(klay "D-FINE")
(entmake (list '(0 . "LINE") (cons 8 "D-FINE") (cons 10 '(135.750000 240.000000 0.000000)) (cons 11 '(135.750000 214.500000 0.000000))))
(klay "D-FINE")
(entmake (list '(0 . "LINE") (cons 8 "D-FINE") (cons 10 '(145.750000 240.000000 0.000000)) (cons 11 '(145.750000 214.500000 0.000000))))
(klay "D-FINE")
(entmake (list '(0 . "LINE") (cons 8 "D-FINE") (cons 10 '(175.250000 240.000000 0.000000)) (cons 11 '(175.250000 214.500000 0.000000))))
(klay "D-FINE")
(entmake (list '(0 . "LINE") (cons 8 "D-FINE") (cons 10 '(177.750000 240.000000 0.000000)) (cons 11 '(177.750000 214.500000 0.000000))))
(klay "D-FINE")
(entmake (list '(0 . "LINE") (cons 8 "D-FINE") (cons 10 '(176.500000 214.000000 0.000000)) (cons 11 '(202.000000 214.000000 0.000000))))
(klay "D-FINE")
(entmake (list '(0 . "LINE") (cons 8 "D-FINE") (cons 10 '(176.500000 199.000000 0.000000)) (cons 11 '(202.000000 199.000000 0.000000))))
(klay "D-FINE")
(entmake (list '(0 . "LINE") (cons 8 "D-FINE") (cons 10 '(176.500000 163.000000 0.000000)) (cons 11 '(202.000000 163.000000 0.000000))))
(klay "D-FINE")
(entmake (list '(0 . "LINE") (cons 8 "D-FINE") (cons 10 '(176.500000 148.000000 0.000000)) (cons 11 '(202.000000 148.000000 0.000000))))
(klay "D-FINE")
(entmake (list '(0 . "LINE") (cons 8 "D-FINE") (cons 10 '(176.500000 124.000000 0.000000)) (cons 11 '(202.000000 124.000000 0.000000))))
(klay "D-FINE")
(entmake (list '(0 . "LINE") (cons 8 "D-FINE") (cons 10 '(176.500000 123.250000 0.000000)) (cons 11 '(202.000000 123.250000 0.000000))))
(klay "D-FINE")
(entmake (list '(0 . "LINE") (cons 8 "D-FINE") (cons 10 '(176.500000 99.250000 0.000000)) (cons 11 '(202.000000 99.250000 0.000000))))
(klay "D-FINE")
(entmake (list '(0 . "LINE") (cons 8 "D-FINE") (cons 10 '(176.500000 78.250000 0.000000)) (cons 11 '(202.000000 78.250000 0.000000))))
(klay "D-FINE")
(entmake (list '(0 . "LINE") (cons 8 "D-FINE") (cons 10 '(176.500000 77.500000 0.000000)) (cons 11 '(202.000000 77.500000 0.000000))))
(klay "D-FINE")
(entmake (list '(0 . "LINE") (cons 8 "D-FINE") (cons 10 '(37.000000 204.750000 0.000000)) (cons 11 '(62.500000 204.750000 0.000000))))
(klay "D-FINE")
(entmake (list '(0 . "LINE") (cons 8 "D-FINE") (cons 10 '(37.000000 204.000000 0.000000)) (cons 11 '(62.500000 204.000000 0.000000))))
(klay "D-FINE")
(entmake (list '(0 . "LINE") (cons 8 "D-FINE") (cons 10 '(37.000000 167.250000 0.000000)) (cons 11 '(62.500000 167.250000 0.000000))))
(klay "D-FINE")
(entmake (list '(0 . "LINE") (cons 8 "D-FINE") (cons 10 '(37.000000 166.500000 0.000000)) (cons 11 '(62.500000 166.500000 0.000000))))
(klay "D-FINE")
(entmake (list '(0 . "LINE") (cons 8 "D-FINE") (cons 10 '(37.000000 129.500000 0.000000)) (cons 11 '(62.500000 129.500000 0.000000))))
(klay "D-FINE")
(entmake (list '(0 . "LINE") (cons 8 "D-FINE") (cons 10 '(37.000000 127.000000 0.000000)) (cons 11 '(62.500000 127.000000 0.000000))))
(klay "D-OUTLINE")
(command "_.RECTANG" '(37.000000 127.000000 0.000000) '(62.500000 204.750000 0.000000))
(klay "D-HIDDEN")
(command "_.RECTANG" '(114.500000 104.250000 0.000000) '(136.500000 167.000000 0.000000))
(klay "D-HIDDEN")
(command "_.RECTANG" '(114.500000 154.250000 0.000000) '(136.500000 167.000000 0.000000))
(klay "D-HIDDEN")
(command "_.RECTANG" '(114.500000 129.250000 0.000000) '(136.500000 154.250000 0.000000))
(klay "D-HIDDEN")
(command "_.RECTANG" '(114.500000 104.250000 0.000000) '(136.500000 129.250000 0.000000))
(klay "D-HIDDEN")
(command "_.RECTANG" '(104.500000 102.000000 0.000000) '(136.500000 103.500000 0.000000))
(klay "D-HIDDEN")
(entmake (list '(0 . "CIRCLE") (cons 8 "D-HIDDEN") (cons 10 '(107.650000 159.000000 0.000000)) (cons 40 6.75)))
(klay "D-HIDDEN")
(entmake (list '(0 . "CIRCLE") (cons 8 "D-HIDDEN") (cons 10 '(107.650000 135.000000 0.000000)) (cons 40 6.75)))
(klay "D-HIDDEN")
(entmake (list '(0 . "CIRCLE") (cons 8 "D-HIDDEN") (cons 10 '(107.650000 111.000000 0.000000)) (cons 40 6.75)))
(klay "D-FINE")
(command "_.RECTANG" '(203.000000 154.750000 0.000000) '(204.500000 206.750000 0.000000))
(klay "D-FINE")
(command "_.RECTANG" '(203.400000 156.250000 0.000000) '(203.600000 205.250000 0.000000))
(klay "D-FINE")
(command "_.RECTANG" '(39.000000 167.750000 0.000000) '(67.375000 203.500000 0.000000))
(klay "D-FINE")
(command "_.RECTANG" '(67.375000 188.000000 0.000000) '(68.175000 202.000000 0.000000))
(klay "D-TEXT")
(entmake (list '(0 . "TEXT") (cons 8 "D-TEXT") (cons 10 '(207.000000 178.000000 0.000000)) (cons 40 1.4) (cons 1 "WINDOW / A502") '(7 . "KITCHEN") '(50 . 0.0)))
(klay "D-OUTLINE")
(entmake (list '(0 . "CIRCLE") (cons 8 "D-OUTLINE") (cons 10 '(149.000000 200.000000 0.000000)) (cons 40 4)))
(klay "D-FINE")
(entmake (list '(0 . "LINE") (cons 8 "D-FINE") (cons 10 '(145.000000 200.000000 0.000000)) (cons 11 '(153.000000 200.000000 0.000000))))
(klay "D-TEXT")
(entmake (list '(0 . "TEXT") (cons 8 "D-TEXT") (cons 10 '(147.900000 200.800000 0.000000)) (cons 40 1.5) (cons 1 "01") '(7 . "KITCHEN") '(50 . 0.0)))
(klay "D-TEXT")
(entmake (list '(0 . "TEXT") (cons 8 "D-TEXT") (cons 10 '(146.700000 197.800000 0.000000)) (cons 40 1.2) (cons 1 "A201") '(7 . "KITCHEN") '(50 . 0.0)))
(klay "D-OUTLINE")
(entmake (list '(0 . "CIRCLE") (cons 8 "D-OUTLINE") (cons 10 '(161.000000 94.000000 0.000000)) (cons 40 4)))
(klay "D-FINE")
(entmake (list '(0 . "LINE") (cons 8 "D-FINE") (cons 10 '(157.000000 94.000000 0.000000)) (cons 11 '(165.000000 94.000000 0.000000))))
(klay "D-TEXT")
(entmake (list '(0 . "TEXT") (cons 8 "D-TEXT") (cons 10 '(159.900000 94.800000 0.000000)) (cons 40 1.5) (cons 1 "02") '(7 . "KITCHEN") '(50 . 0.0)))
(klay "D-TEXT")
(entmake (list '(0 . "TEXT") (cons 8 "D-TEXT") (cons 10 '(158.700000 91.800000 0.000000)) (cons 40 1.2) (cons 1 "A202") '(7 . "KITCHEN") '(50 . 0.0)))
(klay "D-OUTLINE")
(entmake (list '(0 . "CIRCLE") (cons 8 "D-OUTLINE") (cons 10 '(76.000000 119.000000 0.000000)) (cons 40 4)))
(klay "D-FINE")
(entmake (list '(0 . "LINE") (cons 8 "D-FINE") (cons 10 '(72.000000 119.000000 0.000000)) (cons 11 '(80.000000 119.000000 0.000000))))
(klay "D-TEXT")
(entmake (list '(0 . "TEXT") (cons 8 "D-TEXT") (cons 10 '(74.900000 119.800000 0.000000)) (cons 40 1.5) (cons 1 "03") '(7 . "KITCHEN") '(50 . 0.0)))
(klay "D-TEXT")
(entmake (list '(0 . "TEXT") (cons 8 "D-TEXT") (cons 10 '(73.700000 116.800000 0.000000)) (cons 40 1.2) (cons 1 "A203") '(7 . "KITCHEN") '(50 . 0.0)))
(klay "D-TEXT")
(entmake (list '(0 . "TEXT") (cons 8 "D-TEXT") (cons 10 '(115.000000 138.000000 0.000000)) (cons 40 1.5) (cons 1 "A401") '(7 . "KITCHEN") '(50 . 0.0)))
(klay "D-FINE")
(command "_.RECTANG" '(105.625000 213.500000 0.000000) '(135.375000 239.000000 0.000000))
(klay "D-FINE")
(entmake (list '(0 . "CIRCLE") (cons 8 "D-FINE") (cons 10 '(112.000000 232.000000 0.000000)) (cons 40 3)))
(klay "D-FINE")
(entmake (list '(0 . "CIRCLE") (cons 8 "D-FINE") (cons 10 '(128.000000 232.000000 0.000000)) (cons 40 3)))
(klay "D-FINE")
(entmake (list '(0 . "CIRCLE") (cons 8 "D-FINE") (cons 10 '(112.000000 221.000000 0.000000)) (cons 40 4)))
(klay "D-FINE")
(entmake (list '(0 . "CIRCLE") (cons 8 "D-FINE") (cons 10 '(128.000000 221.000000 0.000000)) (cons 40 4)))
(klay "D-OUTLINE")
(command "_.RECTANG" '(58.500000 119.750000 0.000000) '(62.500000 127.000000 0.000000))
(klay "D-OUTLINE")
(command "_.RECTANG" '(59.375000 47.750000 0.000000) '(61.125000 83.750000 0.000000))
(klay "D-OUTLINE")
(command "_.RECTANG" '(58.500000 83.750000 0.000000) '(59.100000 119.750000 0.000000))
(klay "D-OUTLINE")
(command "_.RECTANG" '(61.900000 83.750000 0.000000) '(62.500000 119.750000 0.000000))
(klay "D-OUTLINE")
(command "_.RECTANG" '(58.500000 33.750000 0.000000) '(62.500000 47.750000 0.000000))
(klay "D-OUTLINE")
(command "_.RECTANG" '(61.150000 50.350000 0.000000) '(61.300000 51.650000 0.000000))
(klay "D-OUTLINE")
(entmake (list '(0 . "LINE") (cons 8 "D-OUTLINE") (cons 10 '(56.000000 55.000000 0.000000)) (cons 11 '(56.000000 110.000000 0.000000))))
(klay "D-FINE")
(entmake (list '(0 . "LINE") (cons 8 "D-FINE") (cons 10 '(56.000000 110.000000 0.000000)) (cons 11 '(54.500000 107.000000 0.000000))))
(klay "D-FINE")
(entmake (list '(0 . "LINE") (cons 8 "D-FINE") (cons 10 '(56.000000 110.000000 0.000000)) (cons 11 '(57.500000 107.000000 0.000000))))
(klay "D-FINE")
(entmake (list '(0 . "LINE") (cons 8 "D-FINE") (cons 10 '(58.500000 37.000000 0.000000)) (cons 11 '(60.500000 35.000000 0.000000))))
(klay "D-FINE")
(entmake (list '(0 . "LINE") (cons 8 "D-FINE") (cons 10 '(60.500000 35.000000 0.000000)) (cons 11 '(62.500000 37.000000 0.000000))))
(klay "D-TEXT")
(entmake (list '(0 . "TEXT") (cons 8 "D-TEXT") (cons 10 '(67.000000 67.000000 0.000000)) (cons 40 1.6) (cons 1 "36 x 80 pocket leaf") '(7 . "KITCHEN") '(50 . 0.0)))
(klay "D-TEXT")
(entmake (list '(0 . "TEXT") (cons 8 "D-TEXT") (cons 10 '(67.000000 63.000000 0.000000)) (cons 40 1.5) (cons 1 "slides toward cabinetry / A402") '(7 . "KITCHEN") '(50 . 0.0)))
(klay "D-DIMS")
(command "_.DIMLINEAR" '(37.000000 240.000000 0.000000) '(72.250000 240.000000 0.000000) "_H" '(54.625000 248.000000 0.000000))
(klay "D-DIMS")
(command "_.DIMLINEAR" '(72.250000 240.000000 0.000000) '(95.250000 240.000000 0.000000) "_H" '(83.750000 248.000000 0.000000))
(klay "D-DIMS")
(command "_.DIMLINEAR" '(95.250000 240.000000 0.000000) '(105.250000 240.000000 0.000000) "_H" '(100.250000 248.000000 0.000000))
(klay "D-DIMS")
(command "_.DIMLINEAR" '(105.250000 240.000000 0.000000) '(135.750000 240.000000 0.000000) "_H" '(120.500000 248.000000 0.000000))
(klay "D-DIMS")
(command "_.DIMLINEAR" '(135.750000 240.000000 0.000000) '(145.750000 240.000000 0.000000) "_H" '(140.750000 248.000000 0.000000))
(klay "D-DIMS")
(command "_.DIMLINEAR" '(145.750000 240.000000 0.000000) '(175.250000 240.000000 0.000000) "_H" '(160.500000 248.000000 0.000000))
(klay "D-DIMS")
(command "_.DIMLINEAR" '(175.250000 240.000000 0.000000) '(202.000000 240.000000 0.000000) "_H" '(188.625000 248.000000 0.000000))
(klay "D-DIMS")
(command "_.DIMLINEAR" '(37.000000 240.000000 0.000000) '(202.000000 240.000000 0.000000) "_H" '(119.500000 257.000000 0.000000))
(klay "D-DIMS")
(command "_.DIMLINEAR" '(37.000000 240.000000 0.000000) '(120.500000 240.000000 0.000000) "_H" '(78.750000 265.000000 0.000000))
(klay "D-DIMS")
(command "_.DIMLINEAR" '(37.000000 127.000000 0.000000) '(37.000000 240.000000 0.000000) "_V" '(19.000000 183.500000 0.000000))
(klay "D-DIMS")
(command "_.DIMLINEAR" '(202.000000 76.500000 0.000000) '(202.000000 240.000000 0.000000) "_V" '(226.000000 158.250000 0.000000))
(klay "D-DIMS")
(command "_.DIMLINEAR" '(104.500000 102.000000 0.000000) '(136.500000 102.000000 0.000000) "_H" '(120.500000 92.000000 0.000000))
(klay "D-DIMS")
(command "_.DIMLINEAR" '(136.500000 102.000000 0.000000) '(136.500000 168.000000 0.000000) "_V" '(149.000000 135.000000 0.000000))
(klay "D-DIMS")
(command "_.DIMLINEAR" '(62.500000 142.000000 0.000000) '(104.500000 142.000000 0.000000) "_H" '(83.500000 142.000000 0.000000))
(klay "D-DIMS")
(command "_.DIMLINEAR" '(136.500000 128.000000 0.000000) '(176.000000 128.000000 0.000000) "_H" '(156.250000 128.000000 0.000000))
(klay "D-DIMS")
(command "_.DIMLINEAR" '(120.500000 168.000000 0.000000) '(120.500000 214.000000 0.000000) "_V" '(120.500000 191.000000 0.000000))
(klay "D-TEXT")
(entmake (list '(0 . "TEXT") (cons 8 "D-TEXT") (cons 10 '(41.000000 148.000000 0.000000)) (cons 40 1.7) (cons 1 "37 PANTRY") '(7 . "KITCHEN") '(50 . 0.0)))
(klay "D-TEXT")
(entmake (list '(0 . "TEXT") (cons 8 "D-TEXT") (cons 10 '(41.000000 183.000000 0.000000)) (cons 40 1.7) (cons 1 "LG FRIDGE") '(7 . "KITCHEN") '(50 . 0.0)))
(klay "D-TEXT")
(entmake (list '(0 . "TEXT") (cons 8 "D-TEXT") (cons 10 '(180.000000 135.000000 0.000000)) (cons 40 1.8) (cons 1 "DW") '(7 . "KITCHEN") '(50 . 0.0)))
(klay "D-TEXT")
(entmake (list '(0 . "TEXT") (cons 8 "D-TEXT") (cons 10 '(180.000000 110.000000 0.000000)) (cons 40 1.8) (cons 1 "WINE") '(7 . "KITCHEN") '(50 . 0.0)))
(klay "D-TEXT")
(entmake (list '(0 . "TEXT") (cons 8 "D-TEXT") (cons 10 '(106.000000 95.000000 0.000000)) (cons 40 1.5) (cons 1 "OUTER / LIVING ROOM") '(7 . "KITCHEN") '(50 . 0.0)))
(klay "D-TITLE")
(entmake (list '(0 . "TEXT") (cons 8 "D-TITLE") (cons 10 '(258.000000 246.000000 0.000000)) (cons 40 2.5) (cons 1 "COORDINATION DATUMS") '(7 . "KITCHEN") '(50 . 0.0)))
(klay "D-TEXT")
(entmake (list '(0 . "TEXT") (cons 8 "D-TEXT") (cons 10 '(258.000000 239.000000 0.000000)) (cons 40 1.68) (cons 1 "Origin: back-left finished drywall.") '(7 . "KITCHEN") '(50 . 0.0)))
(klay "D-TEXT")
(entmake (list '(0 . "TEXT") (cons 8 "D-TEXT") (cons 10 '(258.000000 235.960000 0.000000)) (cons 40 1.68) (cons 1 "X across range wall; plan depth D to living room.") '(7 . "KITCHEN") '(50 . 0.0)))
(klay "D-TEXT")
(entmake (list '(0 . "TEXT") (cons 8 "D-TEXT") (cons 10 '(258.000000 232.920000 0.000000)) (cons 40 1.68) (cons 1 "Native WCS Y = -D; Z = height. Ceiling = 108.") '(7 . "KITCHEN") '(50 . 0.0)))
(klay "D-TEXT")
(entmake (list '(0 . "TEXT") (cons 8 "D-TEXT") (cons 10 '(258.000000 229.880000 0.000000)) (cons 40 1.68) (cons 1 "Range and island centreline X = 83.5.") '(7 . "KITCHEN") '(50 . 0.0)))
(klay "D-TEXT")
(entmake (list '(0 . "TEXT") (cons 8 "D-TEXT") (cons 10 '(258.000000 226.840000 0.000000)) (cons 40 1.68) (cons 1 "") '(7 . "KITCHEN") '(50 . 0.0)))
(klay "D-TEXT")
(entmake (list '(0 . "TEXT") (cons 8 "D-TEXT") (cons 10 '(258.000000 223.800000 0.000000)) (cons 40 1.68) (cons 1 "COUNTERTOPS") '(7 . "KITCHEN") '(50 . 0.0)))
(klay "D-TEXT")
(entmake (list '(0 . "TEXT") (cons 8 "D-TEXT") (cons 10 '(258.000000 220.760000 0.000000)) (cons 40 1.68) (cons 1 "12 mm Statuario porcelain throughout.") '(7 . "KITCHEN") '(50 . 0.0)))
(klay "D-TEXT")
(entmake (list '(0 . "TEXT") (cons 8 "D-TEXT") (cons 10 '(258.000000 217.720000 0.000000)) (cons 40 1.68) (cons 1 "36 finished height; 26 perimeter depth.") '(7 . "KITCHEN") '(50 . 0.0)))
(klay "D-TEXT")
(entmake (list '(0 . "TEXT") (cons 8 "D-TEXT") (cons 10 '(258.000000 214.680000 0.000000)) (cons 40 1.68) (cons 1 "Island: 66 x 32; body 22 + overhang 10.") '(7 . "KITCHEN") '(50 . 0.0)))
(klay "D-TEXT")
(entmake (list '(0 . "TEXT") (cons 8 "D-TEXT") (cons 10 '(258.000000 211.640000 0.000000)) (cons 40 1.68) (cons 1 "One waterfall at outer / living-room end.") '(7 . "KITCHEN") '(50 . 0.0)))
(klay "D-TEXT")
(entmake (list '(0 . "TEXT") (cons 8 "D-TEXT") (cons 10 '(258.000000 208.600000 0.000000)) (cons 40 1.68) (cons 1 "") '(7 . "KITCHEN") '(50 . 0.0)))
(klay "D-TEXT")
(entmake (list '(0 . "TEXT") (cons 8 "D-TEXT") (cons 10 '(258.000000 205.560000 0.000000)) (cons 40 1.68) (cons 1 "DIMENSION CHAIN") '(7 . "KITCHEN") '(50 . 0.0)))
(klay "D-TEXT")
(entmake (list '(0 . "TEXT") (cons 8 "D-TEXT") (cons 10 '(258.000000 202.520000 0.000000)) (cons 40 1.68) (cons 1 "165 = 35.25 + 23 + 10 + 30.5") '(7 . "KITCHEN") '(50 . 0.0)))
(klay "D-TEXT")
(entmake (list '(0 . "TEXT") (cons 8 "D-TEXT") (cons 10 '(258.000000 199.480000 0.000000)) (cons 40 1.68) (cons 1 "       + 10 + 29.5 + 2.5 + 24.25") '(7 . "KITCHEN") '(50 . 0.0)))
(klay "D-TEXT")
(entmake (list '(0 . "TEXT") (cons 8 "D-TEXT") (cons 10 '(258.000000 196.440000 0.000000)) (cons 40 1.68) (cons 1 "113 = 35.25 + .75 + 36.75") '(7 . "KITCHEN") '(50 . 0.0)))
(klay "D-TEXT")
(entmake (list '(0 . "TEXT") (cons 8 "D-TEXT") (cons 10 '(258.000000 193.400000 0.000000)) (cons 40 1.68) (cons 1 "       + .75 + 37 + 2.5") '(7 . "KITCHEN") '(50 . 0.0)))
(klay "D-TEXT")
(entmake (list '(0 . "TEXT") (cons 8 "D-TEXT") (cons 10 '(258.000000 190.360000 0.000000)) (cons 40 1.68) (cons 1 "") '(7 . "KITCHEN") '(50 . 0.0)))
(klay "D-TEXT")
(entmake (list '(0 . "TEXT") (cons 8 "D-TEXT") (cons 10 '(258.000000 187.320000 0.000000)) (cons 40 1.68) (cons 1 "FIXED SURFACE GAPS") '(7 . "KITCHEN") '(50 . 0.0)))
(klay "D-TEXT")
(entmake (list '(0 . "TEXT") (cons 8 "D-TEXT") (cons 10 '(258.000000 184.280000 0.000000)) (cons 40 1.68) (cons 1 "Left side 42; sink side 39.5; rear 46.") '(7 . "KITCHEN") '(50 . 0.0)))
(klay "D-TEXT")
(entmake (list '(0 . "TEXT") (cons 8 "D-TEXT") (cons 10 '(258.000000 181.240000 0.000000)) (cons 40 1.68) (cons 1 "These exclude occupants and open doors.") '(7 . "KITCHEN") '(50 . 0.0)))
(klay "D-TEXT")
(entmake (list '(0 . "TEXT") (cons 8 "D-TEXT") (cons 10 '(258.000000 178.200000 0.000000)) (cons 40 1.68) (cons 1 "") '(7 . "KITCHEN") '(50 . 0.0)))
(klay "D-TEXT")
(entmake (list '(0 . "TEXT") (cons 8 "D-TEXT") (cons 10 '(258.000000 175.160000 0.000000)) (cons 40 1.68) (cons 1 "SOURCE / HOLDS") '(7 . "KITCHEN") '(50 . 0.0)))
(klay "D-TEXT")
(entmake (list '(0 . "TEXT") (cons 8 "D-TEXT") (cons 10 '(258.000000 172.120000 0.000000)) (cons 40 1.68) (cons 1 "Cabinet pp. 2-6; Stone R9 S02.") '(7 . "KITCHEN") '(50 . 0.0)))
(klay "D-TEXT")
(entmake (list '(0 . "TEXT") (cons 8 "D-TEXT") (cons 10 '(258.000000 169.080000 0.000000)) (cons 40 1.68) (cons 1 "Window CL / sink / tap: 59.25 nominal.") '(7 . "KITCHEN") '(50 . 0.0)))
(klay "D-TEXT")
(entmake (list '(0 . "TEXT") (cons 8 "D-TEXT") (cons 10 '(258.000000 166.040000 0.000000)) (cons 40 1.68) (cons 1 "Source 1/4 in. discrepancy: field verify.") '(7 . "KITCHEN") '(50 . 0.0)))
(klay "D-TEXT")
(entmake (list '(0 . "TEXT") (cons 8 "D-TEXT") (cons 10 '(258.000000 163.000000 0.000000)) (cons 40 1.68) (cons 1 "Pocket kit and wall construction unselected.") '(7 . "KITCHEN") '(50 . 0.0)))
(klay "D-TEXT")
(entmake (list '(0 . "TEXT") (cons 8 "D-TEXT") (cons 10 '(258.000000 159.960000 0.000000)) (cons 40 1.68) (cons 1 "Wall thickness and adjacent extent contextual.") '(7 . "KITCHEN") '(50 . 0.0)))
(klay "D-TEXT")
(entmake (list '(0 . "TEXT") (cons 8 "D-TEXT") (cons 10 '(258.000000 156.920000 0.000000)) (cons 40 1.68) (cons 1 "Three stools: compact occasional seating.") '(7 . "KITCHEN") '(50 . 0.0)))
(setvar "DIMTXT" 1.26) (setvar "DIMASZ" 0.8999999999999999) (setvar "DIMGAP" 0.48) (setvar "DIMEXO" 0.72) (setvar "DIMEXE" 0.72)
(if (tblsearch "DIMSTYLE" "KITCHEN_1_12") (command "_.-DIMSTYLE" "_S" "KITCHEN_1_12" "_Y") (command "_.-DIMSTYLE" "_S" "KITCHEN_1_12"))
(command "_.-DIMSTYLE" "_R" "KITCHEN_1_12")
(klay "D-TITLE")
(command "_.RECTANG" '(1004.800000 4.800000 0.000000) '(1283.200000 211.200000 0.000000))
(klay "D-TITLE")
(entmake (list '(0 . "LINE") (cons 8 "D-TITLE") (cons 10 '(1004.800000 20.400000 0.000000)) (cons 11 '(1283.200000 20.400000 0.000000))))
(klay "D-TITLE")
(entmake (list '(0 . "TEXT") (cons 8 "D-TITLE") (cons 10 '(1008.400000 9.600000 0.000000)) (cons 40 1.92) (cons 1 "KITCHEN RENOVATION") '(7 . "KITCHEN") '(50 . 0.0)))
(klay "D-TEXT")
(entmake (list '(0 . "TEXT") (cons 8 "D-TEXT") (cons 10 '(1008.400000 6.600000 0.000000)) (cons 40 1.08) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(1183.600000 13.440000 0.000000)) (cons 40 1.6800000000000002) (cons 1 "Range wall elevation") '(7 . "KITCHEN") '(50 . 0.0)))
(klay "D-TEXT")
(entmake (list '(0 . "TEXT") (cons 8 "D-TEXT") (cons 10 '(1183.600000 8.400000 0.000000)) (cons 40 1.1400000000000001) (cons 1 "22 OCT 2026  |  1 in. = 1 ft  |  24 x 18 in.  |  INCHES") '(7 . "KITCHEN") '(50 . 0.0)))
(klay "D-TITLE")
(entmake (list '(0 . "TEXT") (cons 8 "D-TITLE") (cons 10 '(1259.200000 9.000000 0.000000)) (cons 40 4.08) (cons 1 "A201") '(7 . "KITCHEN") '(50 . 0.0)))
(klay "D-TITLE")
(entmake (list '(0 . "TEXT") (cons 8 "D-TITLE") (cons 10 '(1008.400000 205.800000 0.000000)) (cons 40 2.7600000000000002) (cons 1 "RANGE WALL ELEVATION") '(7 . "KITCHEN") '(50 . 0.0)))
(klay "D-TEXT")
(entmake (list '(0 . "TEXT") (cons 8 "D-TEXT") (cons 10 '(1008.400000 202.320000 0.000000)) (cons 40 1.08) (cons 1 "SOURCE COORDINATION / 22 OCT 2026") '(7 . "KITCHEN") '(50 . 0.0)))
(klay "D-OUTLINE")
(command "_.RECTANG" '(1025.000000 63.000000 0.000000) '(1190.000000 171.000000 0.000000))
(klay "D-OUTLINE")
(entmake (list '(0 . "LINE") (cons 8 "D-OUTLINE") (cons 10 '(1025.000000 99.000000 0.000000)) (cons 11 '(1190.000000 99.000000 0.000000))))
(klay "D-FINE")
(entmake (list '(0 . "LINE") (cons 8 "D-FINE") (cons 10 '(1025.000000 119.000000 0.000000)) (cons 11 '(1190.000000 119.000000 0.000000))))
(klay "D-OUTLINE")
(command "_.RECTANG" '(1025.000000 67.000000 0.000000) '(1060.250000 97.500000 0.000000))
(klay "D-FINE")
(entmake (list '(0 . "LINE") (cons 8 "D-FINE") (cons 10 '(1058.250000 79.000000 0.000000)) (cons 11 '(1058.250000 85.000000 0.000000))))
(klay "D-OUTLINE")
(command "_.RECTANG" '(1060.250000 67.000000 0.000000) '(1083.250000 97.500000 0.000000))
(klay "D-FINE")
(entmake (list '(0 . "LINE") (cons 8 "D-FINE") (cons 10 '(1060.250000 79.000000 0.000000)) (cons 11 '(1083.250000 79.000000 0.000000))))
(klay "D-FINE")
(entmake (list '(0 . "LINE") (cons 8 "D-FINE") (cons 10 '(1060.250000 88.250000 0.000000)) (cons 11 '(1083.250000 88.250000 0.000000))))
(klay "D-OUTLINE")
(entmake (list '(0 . "LINE") (cons 8 "D-OUTLINE") (cons 10 '(1069.070000 76.000000 0.000000)) (cons 11 '(1074.430000 76.000000 0.000000))))
(klay "D-OUTLINE")
(entmake (list '(0 . "LINE") (cons 8 "D-OUTLINE") (cons 10 '(1069.070000 85.250000 0.000000)) (cons 11 '(1074.430000 85.250000 0.000000))))
(klay "D-OUTLINE")
(entmake (list '(0 . "LINE") (cons 8 "D-OUTLINE") (cons 10 '(1069.070000 94.500000 0.000000)) (cons 11 '(1074.430000 94.500000 0.000000))))
(klay "D-OUTLINE")
(command "_.RECTANG" '(1083.250000 67.000000 0.000000) '(1093.250000 97.500000 0.000000))
(klay "D-OUTLINE")
(command "_.RECTANG" '(1085.573000 95.962200 0.000000) '(1090.927000 96.237800 0.000000))
(klay "D-OUTLINE")
(command "_.RECTANG" '(1123.750000 67.000000 0.000000) '(1133.750000 97.500000 0.000000))
(klay "D-OUTLINE")
(command "_.RECTANG" '(1126.073000 95.962200 0.000000) '(1131.427000 96.237800 0.000000))
(klay "D-OUTLINE")
(command "_.RECTANG" '(1133.750000 67.000000 0.000000) '(1163.250000 97.500000 0.000000))
(klay "D-FINE")
(entmake (list '(0 . "LINE") (cons 8 "D-FINE") (cons 10 '(1133.750000 79.000000 0.000000)) (cons 11 '(1163.250000 79.000000 0.000000))))
(klay "D-FINE")
(entmake (list '(0 . "LINE") (cons 8 "D-FINE") (cons 10 '(1133.750000 88.250000 0.000000)) (cons 11 '(1163.250000 88.250000 0.000000))))
(klay "D-OUTLINE")
(entmake (list '(0 . "LINE") (cons 8 "D-OUTLINE") (cons 10 '(1145.820000 76.000000 0.000000)) (cons 11 '(1151.180000 76.000000 0.000000))))
(klay "D-OUTLINE")
(entmake (list '(0 . "LINE") (cons 8 "D-OUTLINE") (cons 10 '(1145.820000 85.250000 0.000000)) (cons 11 '(1151.180000 85.250000 0.000000))))
(klay "D-OUTLINE")
(entmake (list '(0 . "LINE") (cons 8 "D-OUTLINE") (cons 10 '(1145.820000 94.500000 0.000000)) (cons 11 '(1151.180000 94.500000 0.000000))))
(klay "D-OUTLINE")
(command "_.RECTANG" '(1165.750000 67.000000 0.000000) '(1190.000000 97.500000 0.000000))
(klay "D-FINE")
(entmake (list '(0 . "LINE") (cons 8 "D-FINE") (cons 10 '(1188.000000 79.000000 0.000000)) (cons 11 '(1188.000000 85.000000 0.000000))))
(klay "D-OUTLINE")
(command "_.RECTANG" '(1093.625000 64.500000 0.000000) '(1123.375000 99.000000 0.000000))
(klay "D-FINE")
(command "_.RECTANG" '(1095.550000 69.600000 0.000000) '(1121.450000 89.400000 0.000000))
(klay "D-OUTLINE")
(command "_.RECTANG" '(1094.000000 93.000000 0.000000) '(1123.000000 98.000000 0.000000))
(klay "D-OUTLINE")
(entmake (list '(0 . "LINE") (cons 8 "D-OUTLINE") (cons 10 '(1097.000000 92.000000 0.000000)) (cons 11 '(1120.000000 92.000000 0.000000))))
(klay "D-OUTLINE")
(command "_.RECTANG" '(1025.000000 119.000000 0.000000) '(1042.250000 169.000000 0.000000))
(klay "D-FINE")
(command "_.RECTANG" '(1040.110000 141.320000 0.000000) '(1040.390000 146.680000 0.000000))
(klay "D-OUTLINE")
(command "_.RECTANG" '(1042.250000 119.000000 0.000000) '(1075.500000 169.000000 0.000000))
(klay "D-FINE")
(entmake (list '(0 . "LINE") (cons 8 "D-FINE") (cons 10 '(1058.875000 119.000000 0.000000)) (cons 11 '(1058.875000 169.000000 0.000000))))
(klay "D-FINE")
(command "_.RECTANG" '(1056.735000 141.320000 0.000000) '(1057.015000 146.680000 0.000000))
(klay "D-FINE")
(command "_.RECTANG" '(1060.735000 141.320000 0.000000) '(1061.015000 146.680000 0.000000))
(klay "D-OUTLINE")
(command "_.RECTANG" '(1141.500000 119.000000 0.000000) '(1172.750000 169.000000 0.000000))
(klay "D-FINE")
(entmake (list '(0 . "LINE") (cons 8 "D-FINE") (cons 10 '(1157.125000 119.000000 0.000000)) (cons 11 '(1157.125000 169.000000 0.000000))))
(klay "D-FINE")
(command "_.RECTANG" '(1154.985000 141.320000 0.000000) '(1155.265000 146.680000 0.000000))
(klay "D-FINE")
(command "_.RECTANG" '(1158.985000 141.320000 0.000000) '(1159.265000 146.680000 0.000000))
(klay "D-OUTLINE")
(command "_.RECTANG" '(1172.750000 119.000000 0.000000) '(1190.000000 169.000000 0.000000))
(klay "D-FINE")
(command "_.RECTANG" '(1187.860000 141.320000 0.000000) '(1188.140000 146.680000 0.000000))
(klay "D-OUTLINE")
(command "_.RECTANG" '(1075.500000 119.000000 0.000000) '(1092.500000 171.000000 0.000000))
(klay "D-TEXT")
(entmake (list '(0 . "TEXT") (cons 8 "D-TEXT") (cons 10 '(1082.000000 145.000000 0.000000)) (cons 40 1.2) (cons 1 "H01") '(7 . "KITCHEN") '(50 . 0.0)))
(klay "D-OUTLINE")
(command "_.RECTANG" '(1092.500000 131.245350 0.000000) '(1108.500000 171.000000 0.000000))
(klay "D-TEXT")
(entmake (list '(0 . "TEXT") (cons 8 "D-TEXT") (cons 10 '(1098.500000 151.122675 0.000000)) (cons 40 1.2) (cons 1 "H02") '(7 . "KITCHEN") '(50 . 0.0)))
(klay "D-OUTLINE")
(command "_.RECTANG" '(1108.500000 131.245350 0.000000) '(1124.500000 171.000000 0.000000))
(klay "D-TEXT")
(entmake (list '(0 . "TEXT") (cons 8 "D-TEXT") (cons 10 '(1114.500000 151.122675 0.000000)) (cons 40 1.2) (cons 1 "H03") '(7 . "KITCHEN") '(50 . 0.0)))
(klay "D-OUTLINE")
(command "_.RECTANG" '(1124.500000 119.000000 0.000000) '(1141.500000 171.000000 0.000000))
(klay "D-TEXT")
(entmake (list '(0 . "TEXT") (cons 8 "D-TEXT") (cons 10 '(1131.000000 145.000000 0.000000)) (cons 40 1.2) (cons 1 "H04") '(7 . "KITCHEN") '(50 . 0.0)))
(klay "D-OUTLINE")
(command "_.RECTANG" '(1093.500000 129.080000 0.000000) '(1123.500000 131.245350 0.000000))
(klay "D-FINE")
(entmake (list '(0 . "LINE") (cons 8 "D-FINE") (cons 10 '(1093.500000 129.000000 0.000000)) (cons 11 '(1123.500000 129.000000 0.000000))))
(klay "D-FINE")
(entmake (list '(0 . "LINE") (cons 8 "D-FINE") (cons 10 '(1025.000000 169.000000 0.000000)) (cons 11 '(1190.000000 169.000000 0.000000))))
(klay "D-FINE")
(entmake (list '(0 . "LINE") (cons 8 "D-FINE") (cons 10 '(1093.250000 99.000000 0.000000)) (cons 11 '(1093.250000 119.000000 0.000000))))
(klay "D-FINE")
(entmake (list '(0 . "LINE") (cons 8 "D-FINE") (cons 10 '(1123.750000 99.000000 0.000000)) (cons 11 '(1123.750000 119.000000 0.000000))))
(klay "D-DIMS")
(command "_.DIMLINEAR" '(1025.000000 63.000000 0.000000) '(1060.250000 63.000000 0.000000) "_H" '(1042.625000 53.000000 0.000000))
(klay "D-DIMS")
(command "_.DIMLINEAR" '(1060.250000 63.000000 0.000000) '(1083.250000 63.000000 0.000000) "_H" '(1071.750000 53.000000 0.000000))
(klay "D-DIMS")
(command "_.DIMLINEAR" '(1083.250000 63.000000 0.000000) '(1093.250000 63.000000 0.000000) "_H" '(1088.250000 53.000000 0.000000))
(klay "D-DIMS")
(command "_.DIMLINEAR" '(1093.250000 63.000000 0.000000) '(1123.750000 63.000000 0.000000) "_H" '(1108.500000 53.000000 0.000000))
(klay "D-DIMS")
(command "_.DIMLINEAR" '(1123.750000 63.000000 0.000000) '(1133.750000 63.000000 0.000000) "_H" '(1128.750000 53.000000 0.000000))
(klay "D-DIMS")
(command "_.DIMLINEAR" '(1133.750000 63.000000 0.000000) '(1163.250000 63.000000 0.000000) "_H" '(1148.500000 53.000000 0.000000))
(klay "D-DIMS")
(command "_.DIMLINEAR" '(1163.250000 63.000000 0.000000) '(1165.750000 63.000000 0.000000) "_H" '(1164.500000 53.000000 0.000000))
(klay "D-DIMS")
(command "_.DIMLINEAR" '(1165.750000 63.000000 0.000000) '(1190.000000 63.000000 0.000000) "_H" '(1177.875000 53.000000 0.000000))
(klay "D-DIMS")
(command "_.DIMLINEAR" '(1025.000000 171.000000 0.000000) '(1190.000000 171.000000 0.000000) "_H" '(1107.500000 186.000000 0.000000))
(klay "D-DIMS")
(command "_.DIMLINEAR" '(1025.000000 63.000000 0.000000) '(1025.000000 171.000000 0.000000) "_V" '(1013.000000 117.000000 0.000000))
(klay "D-DIMS")
(command "_.DIMLINEAR" '(1190.000000 63.000000 0.000000) '(1190.000000 99.000000 0.000000) "_V" '(1198.000000 81.000000 0.000000))
(klay "D-DIMS")
(command "_.DIMLINEAR" '(1124.500000 131.245350 0.000000) '(1124.500000 171.000000 0.000000) "_V" '(1130.000000 151.122675 0.000000))
(klay "D-DIMS")
(command "_.DIMLINEAR" '(1108.500000 99.000000 0.000000) '(1108.500000 129.000000 0.000000) "_V" '(1108.500000 114.000000 0.000000))
(klay "D-DIMS")
(command "_.DIMLINEAR" '(1025.000000 63.000000 0.000000) '(1025.000000 99.000000 0.000000) "_V" '(1019.000000 81.000000 0.000000))
(klay "D-DIMS")
(command "_.DIMLINEAR" '(1025.000000 99.000000 0.000000) '(1025.000000 119.000000 0.000000) "_V" '(1019.000000 109.000000 0.000000))
(klay "D-DIMS")
(command "_.DIMLINEAR" '(1025.000000 119.000000 0.000000) '(1025.000000 169.000000 0.000000) "_V" '(1019.000000 144.000000 0.000000))
(klay "D-DIMS")
(command "_.DIMLINEAR" '(1025.000000 169.000000 0.000000) '(1025.000000 171.000000 0.000000) "_V" '(1019.000000 170.000000 0.000000))
(klay "D-HIDDEN")
(command "_.RECTANG" '(1093.250000 94.000000 0.000000) '(1123.750000 99.000000 0.000000))
(klay "D-TEXT")
(entmake (list '(0 . "TEXT") (cons 8 "D-TEXT") (cons 10 '(1083.800000 70.000000 0.000000)) (cons 40 0.95) (cons 1 "SPICE") '(7 . "KITCHEN") '(50 . 0.0)))
(klay "D-TEXT")
(entmake (list '(0 . "TEXT") (cons 8 "D-TEXT") (cons 10 '(1124.100000 70.000000 0.000000)) (cons 40 0.85) (cons 1 "UTENSIL") '(7 . "KITCHEN") '(50 . 0.0)))
(klay "D-TITLE")
(entmake (list '(0 . "TEXT") (cons 8 "D-TITLE") (cons 10 '(1025.000000 39.000000 0.000000)) (cons 40 2) (cons 1 "01  RANGE WALL / SELECTED HOOD B") '(7 . "KITCHEN") '(50 . 0.0)))
(klay "D-TEXT")
(entmake (list '(0 . "TEXT") (cons 8 "D-TEXT") (cons 10 '(1025.000000 35.000000 0.000000)) (cons 40 1.25) (cons 1 "Full-height pullouts: spice left / utensils right. B03 extends 5 below counter; see A602.") '(7 . "KITCHEN") '(50 . 0.0)))
(klay "D-TEXT")
(entmake (list '(0 . "TEXT") (cons 8 "D-TEXT") (cons 10 '(1211.000000 183.000000 0.000000)) (cons 40 1.26) (cons 1 "MATERIAL / HARDWARE") '(7 . "KITCHEN") '(50 . 0.0)))
(klay "D-TEXT")
(entmake (list '(0 . "TEXT") (cons 8 "D-TEXT") (cons 10 '(1211.000000 180.720000 0.000000)) (cons 40 1.26) (cons 1 "Saba Beige Bolero laminate.") '(7 . "KITCHEN") '(50 . 0.0)))
(klay "D-TEXT")
(entmake (list '(0 . "TEXT") (cons 8 "D-TEXT") (cons 10 '(1211.000000 178.440000 0.000000)) (cons 40 1.26) (cons 1 "Hard Rock Maple interiors.") '(7 . "KITCHEN") '(50 . 0.0)))
(klay "D-TEXT")
(entmake (list '(0 . "TEXT") (cons 8 "D-TEXT") (cons 10 '(1211.000000 176.160000 0.000000)) (cons 40 1.26) (cons 1 "Richelieu nickel pull 6132896195.") '(7 . "KITCHEN") '(50 . 0.0)))
(klay "D-TEXT")
(entmake (list '(0 . "TEXT") (cons 8 "D-TEXT") (cons 10 '(1211.000000 173.880000 0.000000)) (cons 40 1.26) (cons 1 "96 mm centres / 136 mm overall.") '(7 . "KITCHEN") '(50 . 0.0)))
(klay "D-TEXT")
(entmake (list '(0 . "TEXT") (cons 8 "D-TEXT") (cons 10 '(1211.000000 171.600000 0.000000)) (cons 40 1.26) (cons 1 "") '(7 . "KITCHEN") '(50 . 0.0)))
(klay "D-TEXT")
(entmake (list '(0 . "TEXT") (cons 8 "D-TEXT") (cons 10 '(1211.000000 169.320000 0.000000)) (cons 40 1.26) (cons 1 "SELECTED HOOD B") '(7 . "KITCHEN") '(50 . 0.0)))
(klay "D-TEXT")
(entmake (list '(0 . "TEXT") (cons 8 "D-TEXT") (cons 10 '(1211.000000 167.040000 0.000000)) (cons 40 1.26) (cons 1 "Owner coordination: 22 October.") '(7 . "KITCHEN") '(50 . 0.0)))
(klay "D-TEXT")
(entmake (list '(0 . "TEXT") (cons 8 "D-TEXT") (cons 10 '(1211.000000 164.760000 0.000000)) (cons 40 1.26) (cons 1 "Lowest modeled underside = 66.") '(7 . "KITCHEN") '(50 . 0.0)))
(klay "D-TEXT")
(entmake (list '(0 . "TEXT") (cons 8 "D-TEXT") (cons 10 '(1211.000000 162.480000 0.000000)) (cons 40 1.26) (cons 1 "30 above finished electric cooktop.") '(7 . "KITCHEN") '(50 . 0.0)))
(klay "D-TEXT")
(entmake (list '(0 . "TEXT") (cons 8 "D-TEXT") (cons 10 '(1211.000000 160.200000 0.000000)) (cons 40 1.26) (cons 1 "Stone bottom approx. 68-1/4.") '(7 . "KITCHEN") '(50 . 0.0)))
(klay "D-TEXT")
(entmake (list '(0 . "TEXT") (cons 8 "D-TEXT") (cons 10 '(1211.000000 157.920000 0.000000)) (cons 40 1.26) (cons 1 "Centre stone height approx. 39-3/4.") '(7 . "KITCHEN") '(50 . 0.0)))
(klay "D-TEXT")
(entmake (list '(0 . "TEXT") (cons 8 "D-TEXT") (cons 10 '(1211.000000 155.640000 0.000000)) (cons 40 1.26) (cons 1 "Final dimensions against actual Sakura.") '(7 . "KITCHEN") '(50 . 0.0)))
(klay "D-TEXT")
(entmake (list '(0 . "TEXT") (cons 8 "D-TEXT") (cons 10 '(1211.000000 153.360000 0.000000)) (cons 40 1.26) (cons 1 "") '(7 . "KITCHEN") '(50 . 0.0)))
(klay "D-TEXT")
(entmake (list '(0 . "TEXT") (cons 8 "D-TEXT") (cons 10 '(1211.000000 151.080000 0.000000)) (cons 40 1.26) (cons 1 "RANGE PULLOUTS") '(7 . "KITCHEN") '(50 . 0.0)))
(klay "D-TEXT")
(entmake (list '(0 . "TEXT") (cons 8 "D-TEXT") (cons 10 '(1211.000000 148.800000 0.000000)) (cons 40 1.26) (cons 1 "Left 10 bay: spice rack.") '(7 . "KITCHEN") '(50 . 0.0)))
(klay "D-TEXT")
(entmake (list '(0 . "TEXT") (cons 8 "D-TEXT") (cons 10 '(1211.000000 146.520000 0.000000)) (cons 40 1.26) (cons 1 "Right 10 bay: utensil holder.") '(7 . "KITCHEN") '(50 . 0.0)))
(klay "D-TEXT")
(entmake (list '(0 . "TEXT") (cons 8 "D-TEXT") (cons 10 '(1211.000000 144.240000 0.000000)) (cons 40 1.26) (cons 1 "Single full-height fronts; top horizontal pulls.") '(7 . "KITCHEN") '(50 . 0.0)))
(klay "D-TEXT")
(entmake (list '(0 . "TEXT") (cons 8 "D-TEXT") (cons 10 '(1211.000000 141.960000 0.000000)) (cons 40 1.26) (cons 1 "Internal accessory studies: see A402.") '(7 . "KITCHEN") '(50 . 0.0)))
(klay "D-TEXT")
(entmake (list '(0 . "TEXT") (cons 8 "D-TEXT") (cons 10 '(1211.000000 139.680000 0.000000)) (cons 40 1.26) (cons 1 "") '(7 . "KITCHEN") '(50 . 0.0)))
(klay "D-TEXT")
(entmake (list '(0 . "TEXT") (cons 8 "D-TEXT") (cons 10 '(1211.000000 137.400000 0.000000)) (cons 40 1.26) (cons 1 "B03 RANGE BACKSPLASH") '(7 . "KITCHEN") '(50 . 0.0)))
(klay "D-TEXT")
(entmake (list '(0 . "TEXT") (cons 8 "D-TEXT") (cons 10 '(1211.000000 135.120000 0.000000)) (cons 40 1.26) (cons 1 "Lower edge = 31 / 5 below counter.") '(7 . "KITCHEN") '(50 . 0.0)))
(klay "D-TEXT")
(entmake (list '(0 . "TEXT") (cons 8 "D-TEXT") (cons 10 '(1211.000000 132.840000 0.000000)) (cons 40 1.26) (cons 1 "Upper shoulder to selected hood datum.") '(7 . "KITCHEN") '(50 . 0.0)))
(klay "D-TEXT")
(entmake (list '(0 . "TEXT") (cons 8 "D-TEXT") (cons 10 '(1211.000000 130.560000 0.000000)) (cons 40 1.26) (cons 1 "32 upper / 30.5 lower stepped piece.") '(7 . "KITCHEN") '(50 . 0.0)))
(klay "D-TEXT")
(entmake (list '(0 . "TEXT") (cons 8 "D-TEXT") (cons 10 '(1211.000000 128.280000 0.000000)) (cons 40 1.26) (cons 1 "Overall approx. 37-1/4 derived; field verify.") '(7 . "KITCHEN") '(50 . 0.0)))
(klay "D-TEXT")
(entmake (list '(0 . "TEXT") (cons 8 "D-TEXT") (cons 10 '(1211.000000 126.000000 0.000000)) (cons 40 1.26) (cons 1 "Independent of hood-front stone height.") '(7 . "KITCHEN") '(50 . 0.0)))
(klay "D-TEXT")
(entmake (list '(0 . "TEXT") (cons 8 "D-TEXT") (cons 10 '(1211.000000 123.720000 0.000000)) (cons 40 1.26) (cons 1 "") '(7 . "KITCHEN") '(50 . 0.0)))
(klay "D-TEXT")
(entmake (list '(0 . "TEXT") (cons 8 "D-TEXT") (cons 10 '(1211.000000 121.440000 0.000000)) (cons 40 1.26) (cons 1 "SOURCE") '(7 . "KITCHEN") '(50 . 0.0)))
(klay "D-TEXT")
(entmake (list '(0 . "TEXT") (cons 8 "D-TEXT") (cons 10 '(1211.000000 119.160000 0.000000)) (cons 40 1.26) (cons 1 "Owner notes 22 Oct; Cabinet p. 5.") '(7 . "KITCHEN") '(50 . 0.0)))
(klay "D-TEXT")
(entmake (list '(0 . "TEXT") (cons 8 "D-TEXT") (cons 10 '(1211.000000 116.880000 0.000000)) (cons 40 1.26) (cons 1 "Stone R9 S05 / S08; detail A602.") '(7 . "KITCHEN") '(50 . 0.0)))
(setvar "DIMTXT" 1.26) (setvar "DIMASZ" 0.8999999999999999) (setvar "DIMGAP" 0.48) (setvar "DIMEXO" 0.72) (setvar "DIMEXE" 0.72)
(if (tblsearch "DIMSTYLE" "KITCHEN_1_12") (command "_.-DIMSTYLE" "_S" "KITCHEN_1_12" "_Y") (command "_.-DIMSTYLE" "_S" "KITCHEN_1_12"))
(command "_.-DIMSTYLE" "_R" "KITCHEN_1_12")
(klay "D-TITLE")
(command "_.RECTANG" '(2004.800000 4.800000 0.000000) '(2283.200000 211.200000 0.000000))
(klay "D-TITLE")
(entmake (list '(0 . "LINE") (cons 8 "D-TITLE") (cons 10 '(2004.800000 20.400000 0.000000)) (cons 11 '(2283.200000 20.400000 0.000000))))
(klay "D-TITLE")
(entmake (list '(0 . "TEXT") (cons 8 "D-TITLE") (cons 10 '(2008.400000 9.600000 0.000000)) (cons 40 1.92) (cons 1 "KITCHEN RENOVATION") '(7 . "KITCHEN") '(50 . 0.0)))
(klay "D-TEXT")
(entmake (list '(0 . "TEXT") (cons 8 "D-TEXT") (cons 10 '(2008.400000 6.600000 0.000000)) (cons 40 1.08) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(2183.600000 13.440000 0.000000)) (cons 40 1.6800000000000002) (cons 1 "Sink wall elevation") '(7 . "KITCHEN") '(50 . 0.0)))
(klay "D-TEXT")
(entmake (list '(0 . "TEXT") (cons 8 "D-TEXT") (cons 10 '(2183.600000 8.400000 0.000000)) (cons 40 1.1400000000000001) (cons 1 "22 OCT 2026  |  1 in. = 1 ft  |  24 x 18 in.  |  INCHES") '(7 . "KITCHEN") '(50 . 0.0)))
(klay "D-TITLE")
(entmake (list '(0 . "TEXT") (cons 8 "D-TITLE") (cons 10 '(2259.200000 9.000000 0.000000)) (cons 40 4.08) (cons 1 "A202") '(7 . "KITCHEN") '(50 . 0.0)))
(klay "D-TITLE")
(entmake (list '(0 . "TEXT") (cons 8 "D-TITLE") (cons 10 '(2008.400000 205.800000 0.000000)) (cons 40 2.7600000000000002) (cons 1 "SINK WALL ELEVATION") '(7 . "KITCHEN") '(50 . 0.0)))
(klay "D-TEXT")
(entmake (list '(0 . "TEXT") (cons 8 "D-TEXT") (cons 10 '(2008.400000 202.320000 0.000000)) (cons 40 1.08) (cons 1 "SOURCE COORDINATION / 22 OCT 2026") '(7 . "KITCHEN") '(50 . 0.0)))
(klay "D-OUTLINE")
(command "_.RECTANG" '(2025.000000 63.000000 0.000000) '(2188.500000 171.000000 0.000000))
(klay "D-OUTLINE")
(entmake (list '(0 . "LINE") (cons 8 "D-OUTLINE") (cons 10 '(2025.000000 99.000000 0.000000)) (cons 11 '(2188.500000 99.000000 0.000000))))
(klay "D-OUTLINE")
(command "_.RECTANG" '(2025.000000 67.000000 0.000000) '(2051.000000 97.500000 0.000000))
(klay "D-FINE")
(command "_.RECTANG" '(2048.860000 79.570000 0.000000) '(2049.140000 84.930000 0.000000))
(klay "D-OUTLINE")
(command "_.RECTANG" '(2051.000000 67.000000 0.000000) '(2066.000000 97.500000 0.000000))
(klay "D-FINE")
(command "_.RECTANG" '(2063.860000 79.570000 0.000000) '(2064.140000 84.930000 0.000000))
(klay "D-OUTLINE")
(command "_.RECTANG" '(2066.000000 67.000000 0.000000) '(2102.000000 97.500000 0.000000))
(klay "D-FINE")
(entmake (list '(0 . "LINE") (cons 8 "D-FINE") (cons 10 '(2084.000000 67.000000 0.000000)) (cons 11 '(2084.000000 97.500000 0.000000))))
(klay "D-FINE")
(command "_.RECTANG" '(2081.860000 79.570000 0.000000) '(2082.140000 84.930000 0.000000))
(klay "D-FINE")
(command "_.RECTANG" '(2085.860000 79.570000 0.000000) '(2086.140000 84.930000 0.000000))
(klay "D-OUTLINE")
(command "_.RECTANG" '(2102.000000 67.000000 0.000000) '(2117.000000 97.500000 0.000000))
(klay "D-OUTLINE")
(command "_.RECTANG" '(2106.823000 95.962200 0.000000) '(2112.177000 96.237800 0.000000))
(klay "D-TEXT")
(entmake (list '(0 . "TEXT") (cons 8 "D-TEXT") (cons 10 '(2103.000000 71.000000 0.000000)) (cons 40 1.1) (cons 1 "WASTE") '(7 . "KITCHEN") '(50 . 0.0)))
(klay "D-OUTLINE")
(command "_.RECTANG" '(2117.000000 67.000000 0.000000) '(2141.000000 97.500000 0.000000))
(klay "D-FINE")
(command "_.RECTANG" '(2117.250000 68.550000 0.000000) '(2140.750000 96.950000 0.000000))
(klay "D-OUTLINE")
(command "_.RECTANG" '(2120.000000 93.000000 0.000000) '(2138.000000 93.500000 0.000000))
(klay "D-OUTLINE")
(command "_.RECTANG" '(2141.750000 67.000000 0.000000) '(2165.750000 97.500000 0.000000))
(klay "D-FINE")
(command "_.RECTANG" '(2142.750000 68.000000 0.000000) '(2164.750000 96.000000 0.000000))
(klay "D-FINE")
(entmake (list '(0 . "LINE") (cons 8 "D-FINE") (cons 10 '(2142.750000 71.000000 0.000000)) (cons 11 '(2164.750000 71.000000 0.000000))))
(klay "D-FINE")
(entmake (list '(0 . "LINE") (cons 8 "D-FINE") (cons 10 '(2142.750000 76.000000 0.000000)) (cons 11 '(2164.750000 76.000000 0.000000))))
(klay "D-FINE")
(entmake (list '(0 . "LINE") (cons 8 "D-FINE") (cons 10 '(2142.750000 81.000000 0.000000)) (cons 11 '(2164.750000 81.000000 0.000000))))
(klay "D-FINE")
(entmake (list '(0 . "LINE") (cons 8 "D-FINE") (cons 10 '(2142.750000 86.000000 0.000000)) (cons 11 '(2164.750000 86.000000 0.000000))))
(klay "D-FINE")
(entmake (list '(0 . "LINE") (cons 8 "D-FINE") (cons 10 '(2142.750000 91.000000 0.000000)) (cons 11 '(2164.750000 91.000000 0.000000))))
(klay "D-OUTLINE")
(command "_.RECTANG" '(2165.750000 67.000000 0.000000) '(2186.750000 97.500000 0.000000))
(klay "D-FINE")
(entmake (list '(0 . "LINE") (cons 8 "D-FINE") (cons 10 '(2165.750000 79.000000 0.000000)) (cons 11 '(2186.750000 79.000000 0.000000))))
(klay "D-FINE")
(entmake (list '(0 . "LINE") (cons 8 "D-FINE") (cons 10 '(2165.750000 86.000000 0.000000)) (cons 11 '(2186.750000 86.000000 0.000000))))
(klay "D-FINE")
(command "_.RECTANG" '(2173.570000 75.860000 0.000000) '(2178.930000 76.140000 0.000000))
(klay "D-FINE")
(command "_.RECTANG" '(2173.570000 82.860000 0.000000) '(2178.930000 83.140000 0.000000))
(klay "D-FINE")
(command "_.RECTANG" '(2173.570000 94.360000 0.000000) '(2178.930000 94.640000 0.000000))
(klay "D-OUTLINE")
(command "_.RECTANG" '(2025.000000 119.000000 0.000000) '(2041.500000 169.000000 0.000000))
(klay "D-FINE")
(command "_.RECTANG" '(2039.360000 141.320000 0.000000) '(2039.640000 146.680000 0.000000))
(klay "D-OUTLINE")
(command "_.RECTANG" '(2041.500000 119.000000 0.000000) '(2057.250000 169.000000 0.000000))
(klay "D-FINE")
(command "_.RECTANG" '(2055.110000 141.320000 0.000000) '(2055.390000 146.680000 0.000000))
(klay "D-OUTLINE")
(command "_.RECTANG" '(2111.500000 119.000000 0.000000) '(2149.625000 169.000000 0.000000))
(klay "D-FINE")
(entmake (list '(0 . "LINE") (cons 8 "D-FINE") (cons 10 '(2130.562500 119.000000 0.000000)) (cons 11 '(2130.562500 169.000000 0.000000))))
(klay "D-FINE")
(command "_.RECTANG" '(2128.422500 141.320000 0.000000) '(2128.702500 146.680000 0.000000))
(klay "D-FINE")
(command "_.RECTANG" '(2132.422500 141.320000 0.000000) '(2132.702500 146.680000 0.000000))
(klay "D-OUTLINE")
(command "_.RECTANG" '(2149.625000 119.000000 0.000000) '(2187.750000 169.000000 0.000000))
(klay "D-FINE")
(entmake (list '(0 . "LINE") (cons 8 "D-FINE") (cons 10 '(2168.687500 119.000000 0.000000)) (cons 11 '(2168.687500 169.000000 0.000000))))
(klay "D-FINE")
(command "_.RECTANG" '(2166.547500 141.320000 0.000000) '(2166.827500 146.680000 0.000000))
(klay "D-FINE")
(command "_.RECTANG" '(2170.547500 141.320000 0.000000) '(2170.827500 146.680000 0.000000))
(klay "D-OUTLINE")
(command "_.RECTANG" '(2058.250000 107.000000 0.000000) '(2110.250000 155.000000 0.000000))
(klay "D-FINE")
(command "_.RECTANG" '(2059.750000 108.500000 0.000000) '(2108.750000 153.500000 0.000000))
(klay "D-FINE")
(command "_.RECTANG" '(2057.250000 155.000000 0.000000) '(2111.250000 171.000000 0.000000))
(klay "D-FINE")
(command "_.RECTANG" '(2057.250000 119.000000 0.000000) '(2058.250000 155.000000 0.000000))
(klay "D-FINE")
(command "_.RECTANG" '(2110.250000 119.000000 0.000000) '(2111.250000 155.000000 0.000000))
(klay "D-FINE")
(entmake (list '(0 . "LINE") (cons 8 "D-FINE") (cons 10 '(2025.000000 119.000000 0.000000)) (cons 11 '(2058.250000 119.000000 0.000000))))
(klay "D-FINE")
(entmake (list '(0 . "LINE") (cons 8 "D-FINE") (cons 10 '(2110.250000 119.000000 0.000000)) (cons 11 '(2188.500000 119.000000 0.000000))))
(klay "D-OUTLINE")
(entmake (list '(0 . "LINE") (cons 8 "D-OUTLINE") (cons 10 '(2067.000000 97.500000 0.000000)) (cons 11 '(2067.000000 107.000000 0.000000))))
(klay "D-HIDDEN")
(command "_.RECTANG" '(2069.250000 88.480000 0.000000) '(2099.250000 98.500000 0.000000))
(entmod (append (entget (entlast)) '((48 . 0.25))))
(klay "D-OUTLINE")
(command "_.RECTANG" '(2083.187500 99.000000 0.000000) '(2085.312500 99.200000 0.000000))
(klay "D-OUTLINE")
(command "_.RECTANG" '(2083.600000 99.200000 0.000000) '(2084.900000 105.750000 0.000000))
(klay "D-FINE")
(command "_.RECTANG" '(2084.020000 105.750000 0.000000) '(2084.480000 117.400000 0.000000))
(klay "D-OUTLINE")
(command "_.RECTANG" '(2083.450000 105.250000 0.000000) '(2085.050000 109.600000 0.000000))
(klay "D-FINE")
(entmake (list '(0 . "LINE") (cons 8 "D-FINE") (cons 10 '(2083.900000 106.250000 0.000000)) (cons 11 '(2084.600000 106.250000 0.000000))))
(klay "D-FINE")
(entmake (list '(0 . "LINE") (cons 8 "D-FINE") (cons 10 '(2083.900000 107.000000 0.000000)) (cons 11 '(2084.600000 107.000000 0.000000))))
(klay "D-FINE")
(entmake (list '(0 . "LINE") (cons 8 "D-FINE") (cons 10 '(2083.900000 107.750000 0.000000)) (cons 11 '(2084.600000 107.750000 0.000000))))
(klay "D-FINE")
(entmake (list '(0 . "LINE") (cons 8 "D-FINE") (cons 10 '(2083.900000 108.500000 0.000000)) (cons 11 '(2084.600000 108.500000 0.000000))))
(klay "D-FINE")
(entmake (list '(0 . "LINE") (cons 8 "D-FINE") (cons 10 '(2083.900000 109.250000 0.000000)) (cons 11 '(2084.600000 109.250000 0.000000))))
(klay "D-FINE")
(entmake (list '(0 . "LINE") (cons 8 "D-FINE") (cons 10 '(2083.900000 110.000000 0.000000)) (cons 11 '(2084.600000 110.000000 0.000000))))
(klay "D-FINE")
(entmake (list '(0 . "LINE") (cons 8 "D-FINE") (cons 10 '(2083.900000 110.750000 0.000000)) (cons 11 '(2084.600000 110.750000 0.000000))))
(klay "D-FINE")
(entmake (list '(0 . "LINE") (cons 8 "D-FINE") (cons 10 '(2083.900000 111.500000 0.000000)) (cons 11 '(2084.600000 111.500000 0.000000))))
(klay "D-FINE")
(entmake (list '(0 . "LINE") (cons 8 "D-FINE") (cons 10 '(2083.900000 112.250000 0.000000)) (cons 11 '(2084.600000 112.250000 0.000000))))
(klay "D-FINE")
(entmake (list '(0 . "LINE") (cons 8 "D-FINE") (cons 10 '(2083.900000 113.000000 0.000000)) (cons 11 '(2084.600000 113.000000 0.000000))))
(klay "D-FINE")
(entmake (list '(0 . "LINE") (cons 8 "D-FINE") (cons 10 '(2083.900000 113.750000 0.000000)) (cons 11 '(2084.600000 113.750000 0.000000))))
(klay "D-FINE")
(entmake (list '(0 . "LINE") (cons 8 "D-FINE") (cons 10 '(2083.900000 114.500000 0.000000)) (cons 11 '(2084.600000 114.500000 0.000000))))
(klay "D-FINE")
(entmake (list '(0 . "LINE") (cons 8 "D-FINE") (cons 10 '(2083.900000 115.250000 0.000000)) (cons 11 '(2084.600000 115.250000 0.000000))))
(klay "D-FINE")
(entmake (list '(0 . "LINE") (cons 8 "D-FINE") (cons 10 '(2083.900000 116.000000 0.000000)) (cons 11 '(2084.600000 116.000000 0.000000))))
(klay "D-FINE")
(entmake (list '(0 . "LINE") (cons 8 "D-FINE") (cons 10 '(2083.900000 116.750000 0.000000)) (cons 11 '(2084.600000 116.750000 0.000000))))
(klay "D-FINE")
(entmake (list '(0 . "LINE") (cons 8 "D-FINE") (cons 10 '(2083.900000 117.400000 0.000000)) (cons 11 '(2084.600000 117.400000 0.000000))))
(klay "D-FINE")
(entmake (list '(0 . "LINE") (cons 8 "D-FINE") (cons 10 '(2083.900000 117.400000 0.000000)) (cons 11 '(2084.250000 117.750000 0.000000))))
(klay "D-FINE")
(entmake (list '(0 . "LINE") (cons 8 "D-FINE") (cons 10 '(2084.250000 117.750000 0.000000)) (cons 11 '(2084.600000 117.400000 0.000000))))
(klay "D-FINE")
(command "_.RECTANG" '(2085.770000 102.250000 0.000000) '(2086.030000 105.550000 0.000000))
(klay "D-OUTLINE")
(command "_.RECTANG" '(2102.550000 99.000000 0.000000) '(2103.950000 99.300000 0.000000))
(klay "D-FINE")
(command "_.RECTANG" '(2103.090000 99.300000 0.000000) '(2103.410000 110.840000 0.000000))
(klay "D-FINE")
(entmake (list '(0 . "LINE") (cons 8 "D-FINE") (cons 10 '(2103.090000 110.840000 0.000000)) (cons 11 '(2103.250000 111.000000 0.000000))))
(klay "D-FINE")
(entmake (list '(0 . "LINE") (cons 8 "D-FINE") (cons 10 '(2103.250000 111.000000 0.000000)) (cons 11 '(2103.410000 110.840000 0.000000))))
(klay "D-DIMS")
(command "_.DIMLINEAR" '(2025.000000 63.000000 0.000000) '(2051.000000 63.000000 0.000000) "_H" '(2038.000000 53.000000 0.000000))
(klay "D-DIMS")
(command "_.DIMLINEAR" '(2051.000000 63.000000 0.000000) '(2066.000000 63.000000 0.000000) "_H" '(2058.500000 53.000000 0.000000))
(klay "D-DIMS")
(command "_.DIMLINEAR" '(2066.000000 63.000000 0.000000) '(2102.000000 63.000000 0.000000) "_H" '(2084.000000 53.000000 0.000000))
(klay "D-DIMS")
(command "_.DIMLINEAR" '(2102.000000 63.000000 0.000000) '(2117.000000 63.000000 0.000000) "_H" '(2109.500000 53.000000 0.000000))
(klay "D-DIMS")
(command "_.DIMLINEAR" '(2117.000000 63.000000 0.000000) '(2141.000000 63.000000 0.000000) "_H" '(2129.000000 53.000000 0.000000))
(klay "D-DIMS")
(command "_.DIMLINEAR" '(2141.000000 63.000000 0.000000) '(2165.750000 63.000000 0.000000) "_H" '(2153.375000 53.000000 0.000000))
(klay "D-DIMS")
(command "_.DIMLINEAR" '(2165.750000 63.000000 0.000000) '(2187.500000 63.000000 0.000000) "_H" '(2176.625000 53.000000 0.000000))
(klay "D-DIMS")
(command "_.DIMLINEAR" '(2025.000000 171.000000 0.000000) '(2188.500000 171.000000 0.000000) "_H" '(2106.750000 186.000000 0.000000))
(klay "D-DIMS")
(command "_.DIMLINEAR" '(2025.000000 171.000000 0.000000) '(2084.250000 171.000000 0.000000) "_H" '(2054.625000 178.000000 0.000000))
(klay "D-DIMS")
(command "_.DIMLINEAR" '(2025.000000 99.000000 0.000000) '(2067.000000 99.000000 0.000000) "_H" '(2046.000000 102.000000 0.000000))
(klay "D-DIMS")
(command "_.DIMLINEAR" '(2067.000000 99.000000 0.000000) '(2188.500000 99.000000 0.000000) "_H" '(2127.750000 102.000000 0.000000))
(klay "D-DIMS")
(command "_.DIMLINEAR" '(2025.000000 63.000000 0.000000) '(2025.000000 171.000000 0.000000) "_V" '(2013.000000 117.000000 0.000000))
(klay "D-DIMS")
(command "_.DIMLINEAR" '(2188.500000 63.000000 0.000000) '(2188.500000 99.000000 0.000000) "_V" '(2197.000000 81.000000 0.000000))
(klay "D-DIMS")
(command "_.DIMLINEAR" '(2025.000000 63.000000 0.000000) '(2025.000000 99.000000 0.000000) "_V" '(2019.000000 81.000000 0.000000))
(klay "D-DIMS")
(command "_.DIMLINEAR" '(2025.000000 99.000000 0.000000) '(2025.000000 119.000000 0.000000) "_V" '(2019.000000 109.000000 0.000000))
(klay "D-DIMS")
(command "_.DIMLINEAR" '(2025.000000 119.000000 0.000000) '(2025.000000 169.000000 0.000000) "_V" '(2019.000000 144.000000 0.000000))
(klay "D-DIMS")
(command "_.DIMLINEAR" '(2025.000000 169.000000 0.000000) '(2025.000000 171.000000 0.000000) "_V" '(2019.000000 170.000000 0.000000))
(klay "D-TITLE")
(entmake (list '(0 . "TEXT") (cons 8 "D-TITLE") (cons 10 '(2025.000000 39.000000 0.000000)) (cons 40 2) (cons 1 "02  SINK WALL / ALIGNED STONE SEAM") '(7 . "KITCHEN") '(50 . 0.0)))
(klay "D-TEXT")
(entmake (list '(0 . "TEXT") (cons 8 "D-TEXT") (cons 10 '(2025.000000 35.000000 0.000000)) (cons 40 1.3) (cons 1 "Window width 52 nominal; sill 44 and head 92 are retained study levels, subject to field template.") '(7 . "KITCHEN") '(50 . 0.0)))
(klay "D-TEXT")
(entmake (list '(0 . "TEXT") (cons 8 "D-TEXT") (cons 10 '(2211.000000 183.000000 0.000000)) (cons 40 1.26) (cons 1 "COUNTER / BACKSPLASH") '(7 . "KITCHEN") '(50 . 0.0)))
(klay "D-TEXT")
(entmake (list '(0 . "TEXT") (cons 8 "D-TEXT") (cons 10 '(2211.000000 180.720000 0.000000)) (cons 40 1.26) (cons 1 "Base run 162.5; finished counter 163.5.") '(7 . "KITCHEN") '(50 . 0.0)))
(klay "D-TEXT")
(entmake (list '(0 . "TEXT") (cons 8 "D-TEXT") (cons 10 '(2211.000000 178.440000 0.000000)) (cons 40 1.26) (cons 1 "C03 and B06 each 121.5 long.") '(7 . "KITCHEN") '(50 . 0.0)))
(klay "D-TEXT")
(entmake (list '(0 . "TEXT") (cons 8 "D-TEXT") (cons 10 '(2211.000000 176.160000 0.000000)) (cons 40 1.26) (cons 1 "Counter and backsplash seams at 42.") '(7 . "KITCHEN") '(50 . 0.0)))
(klay "D-TEXT")
(entmake (list '(0 . "TEXT") (cons 8 "D-TEXT") (cons 10 '(2211.000000 173.880000 0.000000)) (cons 40 1.26) (cons 1 "B06 continuous shaped piece.") '(7 . "KITCHEN") '(50 . 0.0)))
(klay "D-TEXT")
(entmake (list '(0 . "TEXT") (cons 8 "D-TEXT") (cons 10 '(2211.000000 171.600000 0.000000)) (cons 40 1.26) (cons 1 "") '(7 . "KITCHEN") '(50 . 0.0)))
(klay "D-TEXT")
(entmake (list '(0 . "TEXT") (cons 8 "D-TEXT") (cons 10 '(2211.000000 169.320000 0.000000)) (cons 40 1.26) (cons 1 "WINDOW / SINK HOLD") '(7 . "KITCHEN") '(50 . 0.0)))
(klay "D-TEXT")
(entmake (list '(0 . "TEXT") (cons 8 "D-TEXT") (cons 10 '(2211.000000 167.040000 0.000000)) (cons 40 1.26) (cons 1 "Window / sink / tap CL = 59.25") '(7 . "KITCHEN") '(50 . 0.0)))
(klay "D-TEXT")
(entmake (list '(0 . "TEXT") (cons 8 "D-TEXT") (cons 10 '(2211.000000 164.760000 0.000000)) (cons 40 1.26) (cons 1 "from back-wall drywall, nominal.") '(7 . "KITCHEN") '(50 . 0.0)))
(klay "D-TEXT")
(entmake (list '(0 . "TEXT") (cons 8 "D-TEXT") (cons 10 '(2211.000000 162.480000 0.000000)) (cons 40 1.26) (cons 1 "Cabinet p. 6 flags 1/4 in. discrepancy.") '(7 . "KITCHEN") '(50 . 0.0)))
(klay "D-TEXT")
(entmake (list '(0 . "TEXT") (cons 8 "D-TEXT") (cons 10 '(2211.000000 160.200000 0.000000)) (cons 40 1.26) (cons 1 "Resolve before sink or tap machining.") '(7 . "KITCHEN") '(50 . 0.0)))
(klay "D-TEXT")
(entmake (list '(0 . "TEXT") (cons 8 "D-TEXT") (cons 10 '(2211.000000 157.920000 0.000000)) (cons 40 1.26) (cons 1 "Blinds and internal applied trim removed.") '(7 . "KITCHEN") '(50 . 0.0)))
(klay "D-TEXT")
(entmake (list '(0 . "TEXT") (cons 8 "D-TEXT") (cons 10 '(2211.000000 155.640000 0.000000)) (cons 40 1.26) (cons 1 "W01-W07: seven porcelain pieces.") '(7 . "KITCHEN") '(50 . 0.0)))
(klay "D-TEXT")
(entmake (list '(0 . "TEXT") (cons 8 "D-TEXT") (cons 10 '(2211.000000 153.360000 0.000000)) (cons 40 1.26) (cons 1 "") '(7 . "KITCHEN") '(50 . 0.0)))
(klay "D-TEXT")
(entmake (list '(0 . "TEXT") (cons 8 "D-TEXT") (cons 10 '(2211.000000 151.080000 0.000000)) (cons 40 1.26) (cons 1 "PROPOSED FIXTURES") '(7 . "KITCHEN") '(50 . 0.0)))
(klay "D-TEXT")
(entmake (list '(0 . "TEXT") (cons 8 "D-TEXT") (cons 10 '(2211.000000 148.800000 0.000000)) (cons 40 1.26) (cons 1 "Kraus KWU110-30 sink study.") '(7 . "KITCHEN") '(50 . 0.0)))
(klay "D-TEXT")
(entmake (list '(0 . "TEXT") (cons 8 "D-TEXT") (cons 10 '(2211.000000 146.520000 0.000000)) (cons 40 1.26) (cons 1 "KPF1610 current study: 18.75 high.") '(7 . "KITCHEN") '(50 . 0.0)))
(klay "D-TEXT")
(entmake (list '(0 . "TEXT") (cons 8 "D-TEXT") (cons 10 '(2211.000000 144.240000 0.000000)) (cons 40 1.26) (cons 1 "8.625 reach / 6.25 outlet above deck.") '(7 . "KITCHEN") '(50 . 0.0)))
(klay "D-TEXT")
(entmake (list '(0 . "TEXT") (cons 8 "D-TEXT") (cons 10 '(2211.000000 141.960000 0.000000)) (cons 40 1.26) (cons 1 "Separate filter tap to the right.") '(7 . "KITCHEN") '(50 . 0.0)))
(klay "D-TEXT")
(entmake (list '(0 . "TEXT") (cons 8 "D-TEXT") (cons 10 '(2211.000000 139.680000 0.000000)) (cons 40 1.26) (cons 1 "Final cutout templates and tap offsets") '(7 . "KITCHEN") '(50 . 0.0)))
(klay "D-TEXT")
(entmake (list '(0 . "TEXT") (cons 8 "D-TEXT") (cons 10 '(2211.000000 137.400000 0.000000)) (cons 40 1.26) (cons 1 "must follow selected products.") '(7 . "KITCHEN") '(50 . 0.0)))
(klay "D-TEXT")
(entmake (list '(0 . "TEXT") (cons 8 "D-TEXT") (cons 10 '(2211.000000 135.120000 0.000000)) (cons 40 1.26) (cons 1 "") '(7 . "KITCHEN") '(50 . 0.0)))
(klay "D-TEXT")
(entmake (list '(0 . "TEXT") (cons 8 "D-TEXT") (cons 10 '(2211.000000 132.840000 0.000000)) (cons 40 1.26) (cons 1 "OTHER HOLDS") '(7 . "KITCHEN") '(50 . 0.0)))
(klay "D-TEXT")
(entmake (list '(0 . "TEXT") (cons 8 "D-TEXT") (cons 10 '(2211.000000 130.560000 0.000000)) (cons 40 1.26) (cons 1 "15 in. full-height waste pullout.") '(7 . "KITCHEN") '(50 . 0.0)))
(klay "D-TEXT")
(entmake (list '(0 . "TEXT") (cons 8 "D-TEXT") (cons 10 '(2211.000000 128.280000 0.000000)) (cons 40 1.26) (cons 1 "Tandem garbage / recycling bins.") '(7 . "KITCHEN") '(50 . 0.0)))
(klay "D-TEXT")
(entmake (list '(0 . "TEXT") (cons 8 "D-TEXT") (cons 10 '(2211.000000 126.000000 0.000000)) (cons 40 1.26) (cons 1 "Internal divider/support; see A402.") '(7 . "KITCHEN") '(50 . 0.0)))
(klay "D-TEXT")
(entmake (list '(0 . "TEXT") (cons 8 "D-TEXT") (cons 10 '(2211.000000 123.720000 0.000000)) (cons 40 1.26) (cons 1 "Final bin/hardware selection pending.") '(7 . "KITCHEN") '(50 . 0.0)))
(klay "D-TEXT")
(entmake (list '(0 . "TEXT") (cons 8 "D-TEXT") (cons 10 '(2211.000000 121.440000 0.000000)) (cons 40 1.26) (cons 1 "Counter seam-to-cutout gap: field check.") '(7 . "KITCHEN") '(50 . 0.0)))
(klay "D-TEXT")
(entmake (list '(0 . "TEXT") (cons 8 "D-TEXT") (cons 10 '(2211.000000 119.160000 0.000000)) (cons 40 1.26) (cons 1 "123 slab - 121.5 piece = 1.5 gross") '(7 . "KITCHEN") '(50 . 0.0)))
(klay "D-TEXT")
(entmake (list '(0 . "TEXT") (cons 8 "D-TEXT") (cons 10 '(2211.000000 116.880000 0.000000)) (cons 40 1.26) (cons 1 "before kerf, edge and trim allowances.") '(7 . "KITCHEN") '(50 . 0.0)))
(klay "D-TEXT")
(entmake (list '(0 . "TEXT") (cons 8 "D-TEXT") (cons 10 '(2211.000000 114.600000 0.000000)) (cons 40 1.26) (cons 1 "") '(7 . "KITCHEN") '(50 . 0.0)))
(klay "D-TEXT")
(entmake (list '(0 . "TEXT") (cons 8 "D-TEXT") (cons 10 '(2211.000000 112.320000 0.000000)) (cons 40 1.26) (cons 1 "SOURCE") '(7 . "KITCHEN") '(50 . 0.0)))
(klay "D-TEXT")
(entmake (list '(0 . "TEXT") (cons 8 "D-TEXT") (cons 10 '(2211.000000 110.040000 0.000000)) (cons 40 1.26) (cons 1 "Cabinet p. 6; R9 S03 / S04 / S10.") '(7 . "KITCHEN") '(50 . 0.0)))
(setvar "DIMTXT" 1.26) (setvar "DIMASZ" 0.8999999999999999) (setvar "DIMGAP" 0.48) (setvar "DIMEXO" 0.72) (setvar "DIMEXE" 0.72)
(if (tblsearch "DIMSTYLE" "KITCHEN_1_12") (command "_.-DIMSTYLE" "_S" "KITCHEN_1_12" "_Y") (command "_.-DIMSTYLE" "_S" "KITCHEN_1_12"))
(command "_.-DIMSTYLE" "_R" "KITCHEN_1_12")
(klay "D-TITLE")
(command "_.RECTANG" '(3004.800000 4.800000 0.000000) '(3283.200000 211.200000 0.000000))
(klay "D-TITLE")
(entmake (list '(0 . "LINE") (cons 8 "D-TITLE") (cons 10 '(3004.800000 20.400000 0.000000)) (cons 11 '(3283.200000 20.400000 0.000000))))
(klay "D-TITLE")
(entmake (list '(0 . "TEXT") (cons 8 "D-TITLE") (cons 10 '(3008.400000 9.600000 0.000000)) (cons 40 1.92) (cons 1 "KITCHEN RENOVATION") '(7 . "KITCHEN") '(50 . 0.0)))
(klay "D-TEXT")
(entmake (list '(0 . "TEXT") (cons 8 "D-TEXT") (cons 10 '(3008.400000 6.600000 0.000000)) (cons 40 1.08) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(3183.600000 13.440000 0.000000)) (cons 40 1.6800000000000002) (cons 1 "Pantry and fridge elevation") '(7 . "KITCHEN") '(50 . 0.0)))
(klay "D-TEXT")
(entmake (list '(0 . "TEXT") (cons 8 "D-TEXT") (cons 10 '(3183.600000 8.400000 0.000000)) (cons 40 1.1400000000000001) (cons 1 "22 OCT 2026  |  1 in. = 1 ft  |  24 x 18 in.  |  INCHES") '(7 . "KITCHEN") '(50 . 0.0)))
(klay "D-TITLE")
(entmake (list '(0 . "TEXT") (cons 8 "D-TITLE") (cons 10 '(3259.200000 9.000000 0.000000)) (cons 40 4.08) (cons 1 "A203") '(7 . "KITCHEN") '(50 . 0.0)))
(klay "D-TITLE")
(entmake (list '(0 . "TEXT") (cons 8 "D-TITLE") (cons 10 '(3008.400000 205.800000 0.000000)) (cons 40 2.7600000000000002) (cons 1 "PANTRY AND FRIDGE ELEVATION") '(7 . "KITCHEN") '(50 . 0.0)))
(klay "D-TEXT")
(entmake (list '(0 . "TEXT") (cons 8 "D-TEXT") (cons 10 '(3008.400000 202.320000 0.000000)) (cons 40 1.08) (cons 1 "SOURCE COORDINATION / 22 OCT 2026") '(7 . "KITCHEN") '(50 . 0.0)))
(klay "D-OUTLINE")
(command "_.RECTANG" '(3025.000000 63.000000 0.000000) '(3138.000000 171.000000 0.000000))
(klay "D-FINE")
(command "_.RECTANG" '(3102.750000 63.000000 0.000000) '(3138.000000 171.000000 0.000000))
(klay "D-FINE")
(command "_.RECTANG" '(3102.000000 63.000000 0.000000) '(3102.750000 171.000000 0.000000))
(klay "D-FINE")
(command "_.RECTANG" '(3065.250000 63.000000 0.000000) '(3102.000000 171.000000 0.000000))
(klay "D-FINE")
(command "_.RECTANG" '(3064.500000 63.000000 0.000000) '(3065.250000 171.000000 0.000000))
(klay "D-FINE")
(command "_.RECTANG" '(3027.500000 63.000000 0.000000) '(3064.500000 171.000000 0.000000))
(klay "D-FINE")
(command "_.RECTANG" '(3025.000000 63.000000 0.000000) '(3027.500000 171.000000 0.000000))
(klay "D-OUTLINE")
(command "_.RECTANG" '(3027.500000 67.000000 0.000000) '(3064.500000 83.000000 0.000000))
(klay "D-OUTLINE")
(command "_.RECTANG" '(3027.500000 83.000000 0.000000) '(3064.500000 134.000000 0.000000))
(klay "D-FINE")
(entmake (list '(0 . "LINE") (cons 8 "D-FINE") (cons 10 '(3046.000000 83.000000 0.000000)) (cons 11 '(3046.000000 134.000000 0.000000))))
(klay "D-OUTLINE")
(command "_.RECTANG" '(3027.500000 134.000000 0.000000) '(3064.500000 169.000000 0.000000))
(klay "D-FINE")
(entmake (list '(0 . "LINE") (cons 8 "D-FINE") (cons 10 '(3046.000000 134.000000 0.000000)) (cons 11 '(3046.000000 169.000000 0.000000))))
(klay "D-OUTLINE")
(command "_.RECTANG" '(3065.250000 134.000000 0.000000) '(3102.000000 169.000000 0.000000))
(klay "D-FINE")
(entmake (list '(0 . "LINE") (cons 8 "D-FINE") (cons 10 '(3083.625000 134.000000 0.000000)) (cons 11 '(3083.625000 169.000000 0.000000))))
(klay "D-OUTLINE")
(command "_.RECTANG" '(3065.750000 64.450000 0.000000) '(3101.250000 85.900000 0.000000))
(klay "D-OUTLINE")
(command "_.RECTANG" '(3065.750000 86.000000 0.000000) '(3083.400000 131.875000 0.000000))
(klay "D-OUTLINE")
(command "_.RECTANG" '(3083.600000 86.000000 0.000000) '(3101.250000 131.875000 0.000000))
(klay "D-FINE")
(command "_.RECTANG" '(3085.000000 92.000000 0.000000) '(3099.500000 126.000000 0.000000))
(klay "D-FINE")
(command "_.RECTANG" '(3070.000000 102.000000 0.000000) '(3078.000000 115.000000 0.000000))
(klay "D-OUTLINE")
(entmake (list '(0 . "LINE") (cons 8 "D-OUTLINE") (cons 10 '(3067.000000 84.000000 0.000000)) (cons 11 '(3081.000000 84.000000 0.000000))))
(klay "D-OUTLINE")
(entmake (list '(0 . "LINE") (cons 8 "D-OUTLINE") (cons 10 '(3085.000000 84.000000 0.000000)) (cons 11 '(3099.000000 84.000000 0.000000))))
(klay "D-OUTLINE")
(entmake (list '(0 . "LINE") (cons 8 "D-OUTLINE") (cons 10 '(3081.000000 98.000000 0.000000)) (cons 11 '(3081.000000 121.000000 0.000000))))
(klay "D-OUTLINE")
(entmake (list '(0 . "LINE") (cons 8 "D-OUTLINE") (cons 10 '(3085.000000 98.000000 0.000000)) (cons 11 '(3085.000000 121.000000 0.000000))))
(klay "D-OUTLINE")
(command "_.RECTANG" '(3102.750000 67.000000 0.000000) '(3138.000000 97.500000 0.000000))
(klay "D-OUTLINE")
(command "_.RECTANG" '(3102.750000 119.000000 0.000000) '(3138.000000 169.000000 0.000000))
(klay "D-FINE")
(entmake (list '(0 . "LINE") (cons 8 "D-FINE") (cons 10 '(3102.750000 99.000000 0.000000)) (cons 11 '(3138.000000 99.000000 0.000000))))
(klay "D-DIMS")
(command "_.DIMLINEAR" '(3025.000000 63.000000 0.000000) '(3027.500000 63.000000 0.000000) "_H" '(3026.250000 53.000000 0.000000))
(klay "D-DIMS")
(command "_.DIMLINEAR" '(3027.500000 63.000000 0.000000) '(3064.500000 63.000000 0.000000) "_H" '(3046.000000 53.000000 0.000000))
(klay "D-DIMS")
(command "_.DIMLINEAR" '(3064.500000 63.000000 0.000000) '(3102.750000 63.000000 0.000000) "_H" '(3083.625000 53.000000 0.000000))
(klay "D-DIMS")
(command "_.DIMLINEAR" '(3102.750000 63.000000 0.000000) '(3138.000000 63.000000 0.000000) "_H" '(3120.375000 53.000000 0.000000))
(klay "D-DIMS")
(command "_.DIMLINEAR" '(3025.000000 171.000000 0.000000) '(3138.000000 171.000000 0.000000) "_H" '(3081.500000 186.000000 0.000000))
(klay "D-DIMS")
(command "_.DIMLINEAR" '(3025.000000 63.000000 0.000000) '(3025.000000 171.000000 0.000000) "_V" '(3013.000000 117.000000 0.000000))
(klay "D-DIMS")
(command "_.DIMLINEAR" '(3065.250000 63.000000 0.000000) '(3065.250000 134.000000 0.000000) "_V" '(3064.900000 98.500000 0.000000))
(klay "D-DIMS")
(command "_.DIMLINEAR" '(3025.000000 63.000000 0.000000) '(3025.000000 67.000000 0.000000) "_V" '(3020.000000 65.000000 0.000000))
(klay "D-DIMS")
(command "_.DIMLINEAR" '(3025.000000 67.000000 0.000000) '(3025.000000 83.000000 0.000000) "_V" '(3020.000000 75.000000 0.000000))
(klay "D-DIMS")
(command "_.DIMLINEAR" '(3025.000000 83.000000 0.000000) '(3025.000000 134.000000 0.000000) "_V" '(3020.000000 108.500000 0.000000))
(klay "D-DIMS")
(command "_.DIMLINEAR" '(3025.000000 134.000000 0.000000) '(3025.000000 169.000000 0.000000) "_V" '(3020.000000 151.500000 0.000000))
(klay "D-DIMS")
(command "_.DIMLINEAR" '(3025.000000 169.000000 0.000000) '(3025.000000 171.000000 0.000000) "_V" '(3020.000000 170.000000 0.000000))
(klay "D-OUTLINE")
(command "_.RECTANG" '(3160.000000 63.000000 0.000000) '(3185.500000 171.000000 0.000000))
(klay "D-OUTLINE")
(command "_.RECTANG" '(3160.000000 63.000000 0.000000) '(3160.750000 169.000000 0.000000))
(klay "D-HATCH")
(entmake (list '(0 . "LINE") (cons 8 "D-HATCH") (cons 10 '(3160.000000 64.000000 0.000000)) (cons 11 '(3160.750000 63.250000 0.000000))))
(klay "D-HATCH")
(entmake (list '(0 . "LINE") (cons 8 "D-HATCH") (cons 10 '(3160.000000 65.000000 0.000000)) (cons 11 '(3160.750000 64.250000 0.000000))))
(klay "D-HATCH")
(entmake (list '(0 . "LINE") (cons 8 "D-HATCH") (cons 10 '(3160.000000 66.000000 0.000000)) (cons 11 '(3160.750000 65.250000 0.000000))))
(klay "D-HATCH")
(entmake (list '(0 . "LINE") (cons 8 "D-HATCH") (cons 10 '(3160.000000 67.000000 0.000000)) (cons 11 '(3160.750000 66.250000 0.000000))))
(klay "D-HATCH")
(entmake (list '(0 . "LINE") (cons 8 "D-HATCH") (cons 10 '(3160.000000 68.000000 0.000000)) (cons 11 '(3160.750000 67.250000 0.000000))))
(klay "D-HATCH")
(entmake (list '(0 . "LINE") (cons 8 "D-HATCH") (cons 10 '(3160.000000 69.000000 0.000000)) (cons 11 '(3160.750000 68.250000 0.000000))))
(klay "D-HATCH")
(entmake (list '(0 . "LINE") (cons 8 "D-HATCH") (cons 10 '(3160.000000 70.000000 0.000000)) (cons 11 '(3160.750000 69.250000 0.000000))))
(klay "D-HATCH")
(entmake (list '(0 . "LINE") (cons 8 "D-HATCH") (cons 10 '(3160.000000 71.000000 0.000000)) (cons 11 '(3160.750000 70.250000 0.000000))))
(klay "D-HATCH")
(entmake (list '(0 . "LINE") (cons 8 "D-HATCH") (cons 10 '(3160.000000 72.000000 0.000000)) (cons 11 '(3160.750000 71.250000 0.000000))))
(klay "D-HATCH")
(entmake (list '(0 . "LINE") (cons 8 "D-HATCH") (cons 10 '(3160.000000 73.000000 0.000000)) (cons 11 '(3160.750000 72.250000 0.000000))))
(klay "D-HATCH")
(entmake (list '(0 . "LINE") (cons 8 "D-HATCH") (cons 10 '(3160.000000 74.000000 0.000000)) (cons 11 '(3160.750000 73.250000 0.000000))))
(klay "D-HATCH")
(entmake (list '(0 . "LINE") (cons 8 "D-HATCH") (cons 10 '(3160.000000 75.000000 0.000000)) (cons 11 '(3160.750000 74.250000 0.000000))))
(klay "D-HATCH")
(entmake (list '(0 . "LINE") (cons 8 "D-HATCH") (cons 10 '(3160.000000 76.000000 0.000000)) (cons 11 '(3160.750000 75.250000 0.000000))))
(klay "D-HATCH")
(entmake (list '(0 . "LINE") (cons 8 "D-HATCH") (cons 10 '(3160.000000 77.000000 0.000000)) (cons 11 '(3160.750000 76.250000 0.000000))))
(klay "D-HATCH")
(entmake (list '(0 . "LINE") (cons 8 "D-HATCH") (cons 10 '(3160.000000 78.000000 0.000000)) (cons 11 '(3160.750000 77.250000 0.000000))))
(klay "D-HATCH")
(entmake (list '(0 . "LINE") (cons 8 "D-HATCH") (cons 10 '(3160.000000 79.000000 0.000000)) (cons 11 '(3160.750000 78.250000 0.000000))))
(klay "D-HATCH")
(entmake (list '(0 . "LINE") (cons 8 "D-HATCH") (cons 10 '(3160.000000 80.000000 0.000000)) (cons 11 '(3160.750000 79.250000 0.000000))))
(klay "D-HATCH")
(entmake (list '(0 . "LINE") (cons 8 "D-HATCH") (cons 10 '(3160.000000 81.000000 0.000000)) (cons 11 '(3160.750000 80.250000 0.000000))))
(klay "D-HATCH")
(entmake (list '(0 . "LINE") (cons 8 "D-HATCH") (cons 10 '(3160.000000 82.000000 0.000000)) (cons 11 '(3160.750000 81.250000 0.000000))))
(klay "D-HATCH")
(entmake (list '(0 . "LINE") (cons 8 "D-HATCH") (cons 10 '(3160.000000 83.000000 0.000000)) (cons 11 '(3160.750000 82.250000 0.000000))))
(klay "D-HATCH")
(entmake (list '(0 . "LINE") (cons 8 "D-HATCH") (cons 10 '(3160.000000 84.000000 0.000000)) (cons 11 '(3160.750000 83.250000 0.000000))))
(klay "D-HATCH")
(entmake (list '(0 . "LINE") (cons 8 "D-HATCH") (cons 10 '(3160.000000 85.000000 0.000000)) (cons 11 '(3160.750000 84.250000 0.000000))))
(klay "D-HATCH")
(entmake (list '(0 . "LINE") (cons 8 "D-HATCH") (cons 10 '(3160.000000 86.000000 0.000000)) (cons 11 '(3160.750000 85.250000 0.000000))))
(klay "D-HATCH")
(entmake (list '(0 . "LINE") (cons 8 "D-HATCH") (cons 10 '(3160.000000 87.000000 0.000000)) (cons 11 '(3160.750000 86.250000 0.000000))))
(klay "D-HATCH")
(entmake (list '(0 . "LINE") (cons 8 "D-HATCH") (cons 10 '(3160.000000 88.000000 0.000000)) (cons 11 '(3160.750000 87.250000 0.000000))))
(klay "D-HATCH")
(entmake (list '(0 . "LINE") (cons 8 "D-HATCH") (cons 10 '(3160.000000 89.000000 0.000000)) (cons 11 '(3160.750000 88.250000 0.000000))))
(klay "D-HATCH")
(entmake (list '(0 . "LINE") (cons 8 "D-HATCH") (cons 10 '(3160.000000 90.000000 0.000000)) (cons 11 '(3160.750000 89.250000 0.000000))))
(klay "D-HATCH")
(entmake (list '(0 . "LINE") (cons 8 "D-HATCH") (cons 10 '(3160.000000 91.000000 0.000000)) (cons 11 '(3160.750000 90.250000 0.000000))))
(klay "D-HATCH")
(entmake (list '(0 . "LINE") (cons 8 "D-HATCH") (cons 10 '(3160.000000 92.000000 0.000000)) (cons 11 '(3160.750000 91.250000 0.000000))))
(klay "D-HATCH")
(entmake (list '(0 . "LINE") (cons 8 "D-HATCH") (cons 10 '(3160.000000 93.000000 0.000000)) (cons 11 '(3160.750000 92.250000 0.000000))))
(klay "D-HATCH")
(entmake (list '(0 . "LINE") (cons 8 "D-HATCH") (cons 10 '(3160.000000 94.000000 0.000000)) (cons 11 '(3160.750000 93.250000 0.000000))))
(klay "D-HATCH")
(entmake (list '(0 . "LINE") (cons 8 "D-HATCH") (cons 10 '(3160.000000 95.000000 0.000000)) (cons 11 '(3160.750000 94.250000 0.000000))))
(klay "D-HATCH")
(entmake (list '(0 . "LINE") (cons 8 "D-HATCH") (cons 10 '(3160.000000 96.000000 0.000000)) (cons 11 '(3160.750000 95.250000 0.000000))))
(klay "D-HATCH")
(entmake (list '(0 . "LINE") (cons 8 "D-HATCH") (cons 10 '(3160.000000 97.000000 0.000000)) (cons 11 '(3160.750000 96.250000 0.000000))))
(klay "D-HATCH")
(entmake (list '(0 . "LINE") (cons 8 "D-HATCH") (cons 10 '(3160.000000 98.000000 0.000000)) (cons 11 '(3160.750000 97.250000 0.000000))))
(klay "D-HATCH")
(entmake (list '(0 . "LINE") (cons 8 "D-HATCH") (cons 10 '(3160.000000 99.000000 0.000000)) (cons 11 '(3160.750000 98.250000 0.000000))))
(klay "D-HATCH")
(entmake (list '(0 . "LINE") (cons 8 "D-HATCH") (cons 10 '(3160.000000 100.000000 0.000000)) (cons 11 '(3160.750000 99.250000 0.000000))))
(klay "D-HATCH")
(entmake (list '(0 . "LINE") (cons 8 "D-HATCH") (cons 10 '(3160.000000 101.000000 0.000000)) (cons 11 '(3160.750000 100.250000 0.000000))))
(klay "D-HATCH")
(entmake (list '(0 . "LINE") (cons 8 "D-HATCH") (cons 10 '(3160.000000 102.000000 0.000000)) (cons 11 '(3160.750000 101.250000 0.000000))))
(klay "D-HATCH")
(entmake (list '(0 . "LINE") (cons 8 "D-HATCH") (cons 10 '(3160.000000 103.000000 0.000000)) (cons 11 '(3160.750000 102.250000 0.000000))))
(klay "D-HATCH")
(entmake (list '(0 . "LINE") (cons 8 "D-HATCH") (cons 10 '(3160.000000 104.000000 0.000000)) (cons 11 '(3160.750000 103.250000 0.000000))))
(klay "D-HATCH")
(entmake (list '(0 . "LINE") (cons 8 "D-HATCH") (cons 10 '(3160.000000 105.000000 0.000000)) (cons 11 '(3160.750000 104.250000 0.000000))))
(klay "D-HATCH")
(entmake (list '(0 . "LINE") (cons 8 "D-HATCH") (cons 10 '(3160.000000 106.000000 0.000000)) (cons 11 '(3160.750000 105.250000 0.000000))))
(klay "D-HATCH")
(entmake (list '(0 . "LINE") (cons 8 "D-HATCH") (cons 10 '(3160.000000 107.000000 0.000000)) (cons 11 '(3160.750000 106.250000 0.000000))))
(klay "D-HATCH")
(entmake (list '(0 . "LINE") (cons 8 "D-HATCH") (cons 10 '(3160.000000 108.000000 0.000000)) (cons 11 '(3160.750000 107.250000 0.000000))))
(klay "D-HATCH")
(entmake (list '(0 . "LINE") (cons 8 "D-HATCH") (cons 10 '(3160.000000 109.000000 0.000000)) (cons 11 '(3160.750000 108.250000 0.000000))))
(klay "D-HATCH")
(entmake (list '(0 . "LINE") (cons 8 "D-HATCH") (cons 10 '(3160.000000 110.000000 0.000000)) (cons 11 '(3160.750000 109.250000 0.000000))))
(klay "D-HATCH")
(entmake (list '(0 . "LINE") (cons 8 "D-HATCH") (cons 10 '(3160.000000 111.000000 0.000000)) (cons 11 '(3160.750000 110.250000 0.000000))))
(klay "D-HATCH")
(entmake (list '(0 . "LINE") (cons 8 "D-HATCH") (cons 10 '(3160.000000 112.000000 0.000000)) (cons 11 '(3160.750000 111.250000 0.000000))))
(klay "D-HATCH")
(entmake (list '(0 . "LINE") (cons 8 "D-HATCH") (cons 10 '(3160.000000 113.000000 0.000000)) (cons 11 '(3160.750000 112.250000 0.000000))))
(klay "D-HATCH")
(entmake (list '(0 . "LINE") (cons 8 "D-HATCH") (cons 10 '(3160.000000 114.000000 0.000000)) (cons 11 '(3160.750000 113.250000 0.000000))))
(klay "D-HATCH")
(entmake (list '(0 . "LINE") (cons 8 "D-HATCH") (cons 10 '(3160.000000 115.000000 0.000000)) (cons 11 '(3160.750000 114.250000 0.000000))))
(klay "D-HATCH")
(entmake (list '(0 . "LINE") (cons 8 "D-HATCH") (cons 10 '(3160.000000 116.000000 0.000000)) (cons 11 '(3160.750000 115.250000 0.000000))))
(klay "D-HATCH")
(entmake (list '(0 . "LINE") (cons 8 "D-HATCH") (cons 10 '(3160.000000 117.000000 0.000000)) (cons 11 '(3160.750000 116.250000 0.000000))))
(klay "D-HATCH")
(entmake (list '(0 . "LINE") (cons 8 "D-HATCH") (cons 10 '(3160.000000 118.000000 0.000000)) (cons 11 '(3160.750000 117.250000 0.000000))))
(klay "D-HATCH")
(entmake (list '(0 . "LINE") (cons 8 "D-HATCH") (cons 10 '(3160.000000 119.000000 0.000000)) (cons 11 '(3160.750000 118.250000 0.000000))))
(klay "D-HATCH")
(entmake (list '(0 . "LINE") (cons 8 "D-HATCH") (cons 10 '(3160.000000 120.000000 0.000000)) (cons 11 '(3160.750000 119.250000 0.000000))))
(klay "D-HATCH")
(entmake (list '(0 . "LINE") (cons 8 "D-HATCH") (cons 10 '(3160.000000 121.000000 0.000000)) (cons 11 '(3160.750000 120.250000 0.000000))))
(klay "D-HATCH")
(entmake (list '(0 . "LINE") (cons 8 "D-HATCH") (cons 10 '(3160.000000 122.000000 0.000000)) (cons 11 '(3160.750000 121.250000 0.000000))))
(klay "D-HATCH")
(entmake (list '(0 . "LINE") (cons 8 "D-HATCH") (cons 10 '(3160.000000 123.000000 0.000000)) (cons 11 '(3160.750000 122.250000 0.000000))))
(klay "D-HATCH")
(entmake (list '(0 . "LINE") (cons 8 "D-HATCH") (cons 10 '(3160.000000 124.000000 0.000000)) (cons 11 '(3160.750000 123.250000 0.000000))))
(klay "D-HATCH")
(entmake (list '(0 . "LINE") (cons 8 "D-HATCH") (cons 10 '(3160.000000 125.000000 0.000000)) (cons 11 '(3160.750000 124.250000 0.000000))))
(klay "D-HATCH")
(entmake (list '(0 . "LINE") (cons 8 "D-HATCH") (cons 10 '(3160.000000 126.000000 0.000000)) (cons 11 '(3160.750000 125.250000 0.000000))))
(klay "D-HATCH")
(entmake (list '(0 . "LINE") (cons 8 "D-HATCH") (cons 10 '(3160.000000 127.000000 0.000000)) (cons 11 '(3160.750000 126.250000 0.000000))))
(klay "D-HATCH")
(entmake (list '(0 . "LINE") (cons 8 "D-HATCH") (cons 10 '(3160.000000 128.000000 0.000000)) (cons 11 '(3160.750000 127.250000 0.000000))))
(klay "D-HATCH")
(entmake (list '(0 . "LINE") (cons 8 "D-HATCH") (cons 10 '(3160.000000 129.000000 0.000000)) (cons 11 '(3160.750000 128.250000 0.000000))))
(klay "D-HATCH")
(entmake (list '(0 . "LINE") (cons 8 "D-HATCH") (cons 10 '(3160.000000 130.000000 0.000000)) (cons 11 '(3160.750000 129.250000 0.000000))))
(klay "D-HATCH")
(entmake (list '(0 . "LINE") (cons 8 "D-HATCH") (cons 10 '(3160.000000 131.000000 0.000000)) (cons 11 '(3160.750000 130.250000 0.000000))))
(klay "D-HATCH")
(entmake (list '(0 . "LINE") (cons 8 "D-HATCH") (cons 10 '(3160.000000 132.000000 0.000000)) (cons 11 '(3160.750000 131.250000 0.000000))))
(klay "D-HATCH")
(entmake (list '(0 . "LINE") (cons 8 "D-HATCH") (cons 10 '(3160.000000 133.000000 0.000000)) (cons 11 '(3160.750000 132.250000 0.000000))))
(klay "D-HATCH")
(entmake (list '(0 . "LINE") (cons 8 "D-HATCH") (cons 10 '(3160.000000 134.000000 0.000000)) (cons 11 '(3160.750000 133.250000 0.000000))))
(klay "D-HATCH")
(entmake (list '(0 . "LINE") (cons 8 "D-HATCH") (cons 10 '(3160.000000 135.000000 0.000000)) (cons 11 '(3160.750000 134.250000 0.000000))))
(klay "D-HATCH")
(entmake (list '(0 . "LINE") (cons 8 "D-HATCH") (cons 10 '(3160.000000 136.000000 0.000000)) (cons 11 '(3160.750000 135.250000 0.000000))))
(klay "D-HATCH")
(entmake (list '(0 . "LINE") (cons 8 "D-HATCH") (cons 10 '(3160.000000 137.000000 0.000000)) (cons 11 '(3160.750000 136.250000 0.000000))))
(klay "D-HATCH")
(entmake (list '(0 . "LINE") (cons 8 "D-HATCH") (cons 10 '(3160.000000 138.000000 0.000000)) (cons 11 '(3160.750000 137.250000 0.000000))))
(klay "D-HATCH")
(entmake (list '(0 . "LINE") (cons 8 "D-HATCH") (cons 10 '(3160.000000 139.000000 0.000000)) (cons 11 '(3160.750000 138.250000 0.000000))))
(klay "D-HATCH")
(entmake (list '(0 . "LINE") (cons 8 "D-HATCH") (cons 10 '(3160.000000 140.000000 0.000000)) (cons 11 '(3160.750000 139.250000 0.000000))))
(klay "D-HATCH")
(entmake (list '(0 . "LINE") (cons 8 "D-HATCH") (cons 10 '(3160.000000 141.000000 0.000000)) (cons 11 '(3160.750000 140.250000 0.000000))))
(klay "D-HATCH")
(entmake (list '(0 . "LINE") (cons 8 "D-HATCH") (cons 10 '(3160.000000 142.000000 0.000000)) (cons 11 '(3160.750000 141.250000 0.000000))))
(klay "D-HATCH")
(entmake (list '(0 . "LINE") (cons 8 "D-HATCH") (cons 10 '(3160.000000 143.000000 0.000000)) (cons 11 '(3160.750000 142.250000 0.000000))))
(klay "D-HATCH")
(entmake (list '(0 . "LINE") (cons 8 "D-HATCH") (cons 10 '(3160.000000 144.000000 0.000000)) (cons 11 '(3160.750000 143.250000 0.000000))))
(klay "D-HATCH")
(entmake (list '(0 . "LINE") (cons 8 "D-HATCH") (cons 10 '(3160.000000 145.000000 0.000000)) (cons 11 '(3160.750000 144.250000 0.000000))))
(klay "D-HATCH")
(entmake (list '(0 . "LINE") (cons 8 "D-HATCH") (cons 10 '(3160.000000 146.000000 0.000000)) (cons 11 '(3160.750000 145.250000 0.000000))))
(klay "D-HATCH")
(entmake (list '(0 . "LINE") (cons 8 "D-HATCH") (cons 10 '(3160.000000 147.000000 0.000000)) (cons 11 '(3160.750000 146.250000 0.000000))))
(klay "D-HATCH")
(entmake (list '(0 . "LINE") (cons 8 "D-HATCH") (cons 10 '(3160.000000 148.000000 0.000000)) (cons 11 '(3160.750000 147.250000 0.000000))))
(klay "D-HATCH")
(entmake (list '(0 . "LINE") (cons 8 "D-HATCH") (cons 10 '(3160.000000 149.000000 0.000000)) (cons 11 '(3160.750000 148.250000 0.000000))))
(klay "D-HATCH")
(entmake (list '(0 . "LINE") (cons 8 "D-HATCH") (cons 10 '(3160.000000 150.000000 0.000000)) (cons 11 '(3160.750000 149.250000 0.000000))))
(klay "D-HATCH")
(entmake (list '(0 . "LINE") (cons 8 "D-HATCH") (cons 10 '(3160.000000 151.000000 0.000000)) (cons 11 '(3160.750000 150.250000 0.000000))))
(klay "D-HATCH")
(entmake (list '(0 . "LINE") (cons 8 "D-HATCH") (cons 10 '(3160.000000 152.000000 0.000000)) (cons 11 '(3160.750000 151.250000 0.000000))))
(klay "D-HATCH")
(entmake (list '(0 . "LINE") (cons 8 "D-HATCH") (cons 10 '(3160.000000 153.000000 0.000000)) (cons 11 '(3160.750000 152.250000 0.000000))))
(klay "D-HATCH")
(entmake (list '(0 . "LINE") (cons 8 "D-HATCH") (cons 10 '(3160.000000 154.000000 0.000000)) (cons 11 '(3160.750000 153.250000 0.000000))))
(klay "D-HATCH")
(entmake (list '(0 . "LINE") (cons 8 "D-HATCH") (cons 10 '(3160.000000 155.000000 0.000000)) (cons 11 '(3160.750000 154.250000 0.000000))))
(klay "D-HATCH")
(entmake (list '(0 . "LINE") (cons 8 "D-HATCH") (cons 10 '(3160.000000 156.000000 0.000000)) (cons 11 '(3160.750000 155.250000 0.000000))))
(klay "D-HATCH")
(entmake (list '(0 . "LINE") (cons 8 "D-HATCH") (cons 10 '(3160.000000 157.000000 0.000000)) (cons 11 '(3160.750000 156.250000 0.000000))))
(klay "D-HATCH")
(entmake (list '(0 . "LINE") (cons 8 "D-HATCH") (cons 10 '(3160.000000 158.000000 0.000000)) (cons 11 '(3160.750000 157.250000 0.000000))))
(klay "D-HATCH")
(entmake (list '(0 . "LINE") (cons 8 "D-HATCH") (cons 10 '(3160.000000 159.000000 0.000000)) (cons 11 '(3160.750000 158.250000 0.000000))))
(klay "D-HATCH")
(entmake (list '(0 . "LINE") (cons 8 "D-HATCH") (cons 10 '(3160.000000 160.000000 0.000000)) (cons 11 '(3160.750000 159.250000 0.000000))))
(klay "D-HATCH")
(entmake (list '(0 . "LINE") (cons 8 "D-HATCH") (cons 10 '(3160.000000 161.000000 0.000000)) (cons 11 '(3160.750000 160.250000 0.000000))))
(klay "D-HATCH")
(entmake (list '(0 . "LINE") (cons 8 "D-HATCH") (cons 10 '(3160.000000 162.000000 0.000000)) (cons 11 '(3160.750000 161.250000 0.000000))))
(klay "D-HATCH")
(entmake (list '(0 . "LINE") (cons 8 "D-HATCH") (cons 10 '(3160.000000 163.000000 0.000000)) (cons 11 '(3160.750000 162.250000 0.000000))))
(klay "D-HATCH")
(entmake (list '(0 . "LINE") (cons 8 "D-HATCH") (cons 10 '(3160.000000 164.000000 0.000000)) (cons 11 '(3160.750000 163.250000 0.000000))))
(klay "D-HATCH")
(entmake (list '(0 . "LINE") (cons 8 "D-HATCH") (cons 10 '(3160.000000 165.000000 0.000000)) (cons 11 '(3160.750000 164.250000 0.000000))))
(klay "D-HATCH")
(entmake (list '(0 . "LINE") (cons 8 "D-HATCH") (cons 10 '(3160.000000 166.000000 0.000000)) (cons 11 '(3160.750000 165.250000 0.000000))))
(klay "D-HATCH")
(entmake (list '(0 . "LINE") (cons 8 "D-HATCH") (cons 10 '(3160.000000 167.000000 0.000000)) (cons 11 '(3160.750000 166.250000 0.000000))))
(klay "D-HATCH")
(entmake (list '(0 . "LINE") (cons 8 "D-HATCH") (cons 10 '(3160.000000 168.000000 0.000000)) (cons 11 '(3160.750000 167.250000 0.000000))))
(klay "D-HATCH")
(entmake (list '(0 . "LINE") (cons 8 "D-HATCH") (cons 10 '(3160.000000 169.000000 0.000000)) (cons 11 '(3160.750000 168.250000 0.000000))))
(klay "D-OUTLINE")
(command "_.RECTANG" '(3160.000000 134.000000 0.000000) '(3184.750000 134.750000 0.000000))
(klay "D-HATCH")
(entmake (list '(0 . "LINE") (cons 8 "D-HATCH") (cons 10 '(3160.250000 134.750000 0.000000)) (cons 11 '(3161.000000 134.000000 0.000000))))
(klay "D-HATCH")
(entmake (list '(0 . "LINE") (cons 8 "D-HATCH") (cons 10 '(3161.250000 134.750000 0.000000)) (cons 11 '(3162.000000 134.000000 0.000000))))
(klay "D-HATCH")
(entmake (list '(0 . "LINE") (cons 8 "D-HATCH") (cons 10 '(3162.250000 134.750000 0.000000)) (cons 11 '(3163.000000 134.000000 0.000000))))
(klay "D-HATCH")
(entmake (list '(0 . "LINE") (cons 8 "D-HATCH") (cons 10 '(3163.250000 134.750000 0.000000)) (cons 11 '(3164.000000 134.000000 0.000000))))
(klay "D-HATCH")
(entmake (list '(0 . "LINE") (cons 8 "D-HATCH") (cons 10 '(3164.250000 134.750000 0.000000)) (cons 11 '(3165.000000 134.000000 0.000000))))
(klay "D-HATCH")
(entmake (list '(0 . "LINE") (cons 8 "D-HATCH") (cons 10 '(3165.250000 134.750000 0.000000)) (cons 11 '(3166.000000 134.000000 0.000000))))
(klay "D-HATCH")
(entmake (list '(0 . "LINE") (cons 8 "D-HATCH") (cons 10 '(3166.250000 134.750000 0.000000)) (cons 11 '(3167.000000 134.000000 0.000000))))
(klay "D-HATCH")
(entmake (list '(0 . "LINE") (cons 8 "D-HATCH") (cons 10 '(3167.250000 134.750000 0.000000)) (cons 11 '(3168.000000 134.000000 0.000000))))
(klay "D-HATCH")
(entmake (list '(0 . "LINE") (cons 8 "D-HATCH") (cons 10 '(3168.250000 134.750000 0.000000)) (cons 11 '(3169.000000 134.000000 0.000000))))
(klay "D-HATCH")
(entmake (list '(0 . "LINE") (cons 8 "D-HATCH") (cons 10 '(3169.250000 134.750000 0.000000)) (cons 11 '(3170.000000 134.000000 0.000000))))
(klay "D-HATCH")
(entmake (list '(0 . "LINE") (cons 8 "D-HATCH") (cons 10 '(3170.250000 134.750000 0.000000)) (cons 11 '(3171.000000 134.000000 0.000000))))
(klay "D-HATCH")
(entmake (list '(0 . "LINE") (cons 8 "D-HATCH") (cons 10 '(3171.250000 134.750000 0.000000)) (cons 11 '(3172.000000 134.000000 0.000000))))
(klay "D-HATCH")
(entmake (list '(0 . "LINE") (cons 8 "D-HATCH") (cons 10 '(3172.250000 134.750000 0.000000)) (cons 11 '(3173.000000 134.000000 0.000000))))
(klay "D-HATCH")
(entmake (list '(0 . "LINE") (cons 8 "D-HATCH") (cons 10 '(3173.250000 134.750000 0.000000)) (cons 11 '(3174.000000 134.000000 0.000000))))
(klay "D-HATCH")
(entmake (list '(0 . "LINE") (cons 8 "D-HATCH") (cons 10 '(3174.250000 134.750000 0.000000)) (cons 11 '(3175.000000 134.000000 0.000000))))
(klay "D-HATCH")
(entmake (list '(0 . "LINE") (cons 8 "D-HATCH") (cons 10 '(3175.250000 134.750000 0.000000)) (cons 11 '(3176.000000 134.000000 0.000000))))
(klay "D-HATCH")
(entmake (list '(0 . "LINE") (cons 8 "D-HATCH") (cons 10 '(3176.250000 134.750000 0.000000)) (cons 11 '(3177.000000 134.000000 0.000000))))
(klay "D-HATCH")
(entmake (list '(0 . "LINE") (cons 8 "D-HATCH") (cons 10 '(3177.250000 134.750000 0.000000)) (cons 11 '(3178.000000 134.000000 0.000000))))
(klay "D-HATCH")
(entmake (list '(0 . "LINE") (cons 8 "D-HATCH") (cons 10 '(3178.250000 134.750000 0.000000)) (cons 11 '(3179.000000 134.000000 0.000000))))
(klay "D-HATCH")
(entmake (list '(0 . "LINE") (cons 8 "D-HATCH") (cons 10 '(3179.250000 134.750000 0.000000)) (cons 11 '(3180.000000 134.000000 0.000000))))
(klay "D-HATCH")
(entmake (list '(0 . "LINE") (cons 8 "D-HATCH") (cons 10 '(3180.250000 134.750000 0.000000)) (cons 11 '(3181.000000 134.000000 0.000000))))
(klay "D-HATCH")
(entmake (list '(0 . "LINE") (cons 8 "D-HATCH") (cons 10 '(3181.250000 134.750000 0.000000)) (cons 11 '(3182.000000 134.000000 0.000000))))
(klay "D-HATCH")
(entmake (list '(0 . "LINE") (cons 8 "D-HATCH") (cons 10 '(3182.250000 134.750000 0.000000)) (cons 11 '(3183.000000 134.000000 0.000000))))
(klay "D-HATCH")
(entmake (list '(0 . "LINE") (cons 8 "D-HATCH") (cons 10 '(3183.250000 134.750000 0.000000)) (cons 11 '(3184.000000 134.000000 0.000000))))
(klay "D-HATCH")
(entmake (list '(0 . "LINE") (cons 8 "D-HATCH") (cons 10 '(3184.250000 134.750000 0.000000)) (cons 11 '(3184.750000 134.250000 0.000000))))
(klay "D-OUTLINE")
(command "_.RECTANG" '(3160.000000 169.000000 0.000000) '(3185.500000 171.000000 0.000000))
(klay "D-HATCH")
(entmake (list '(0 . "LINE") (cons 8 "D-HATCH") (cons 10 '(3160.000000 170.000000 0.000000)) (cons 11 '(3161.000000 169.000000 0.000000))))
(klay "D-HATCH")
(entmake (list '(0 . "LINE") (cons 8 "D-HATCH") (cons 10 '(3160.000000 171.000000 0.000000)) (cons 11 '(3162.000000 169.000000 0.000000))))
(klay "D-HATCH")
(entmake (list '(0 . "LINE") (cons 8 "D-HATCH") (cons 10 '(3161.000000 171.000000 0.000000)) (cons 11 '(3163.000000 169.000000 0.000000))))
(klay "D-HATCH")
(entmake (list '(0 . "LINE") (cons 8 "D-HATCH") (cons 10 '(3162.000000 171.000000 0.000000)) (cons 11 '(3164.000000 169.000000 0.000000))))
(klay "D-HATCH")
(entmake (list '(0 . "LINE") (cons 8 "D-HATCH") (cons 10 '(3163.000000 171.000000 0.000000)) (cons 11 '(3165.000000 169.000000 0.000000))))
(klay "D-HATCH")
(entmake (list '(0 . "LINE") (cons 8 "D-HATCH") (cons 10 '(3164.000000 171.000000 0.000000)) (cons 11 '(3166.000000 169.000000 0.000000))))
(klay "D-HATCH")
(entmake (list '(0 . "LINE") (cons 8 "D-HATCH") (cons 10 '(3165.000000 171.000000 0.000000)) (cons 11 '(3167.000000 169.000000 0.000000))))
(klay "D-HATCH")
(entmake (list '(0 . "LINE") (cons 8 "D-HATCH") (cons 10 '(3166.000000 171.000000 0.000000)) (cons 11 '(3168.000000 169.000000 0.000000))))
(klay "D-HATCH")
(entmake (list '(0 . "LINE") (cons 8 "D-HATCH") (cons 10 '(3167.000000 171.000000 0.000000)) (cons 11 '(3169.000000 169.000000 0.000000))))
(klay "D-HATCH")
(entmake (list '(0 . "LINE") (cons 8 "D-HATCH") (cons 10 '(3168.000000 171.000000 0.000000)) (cons 11 '(3170.000000 169.000000 0.000000))))
(klay "D-HATCH")
(entmake (list '(0 . "LINE") (cons 8 "D-HATCH") (cons 10 '(3169.000000 171.000000 0.000000)) (cons 11 '(3171.000000 169.000000 0.000000))))
(klay "D-HATCH")
(entmake (list '(0 . "LINE") (cons 8 "D-HATCH") (cons 10 '(3170.000000 171.000000 0.000000)) (cons 11 '(3172.000000 169.000000 0.000000))))
(klay "D-HATCH")
(entmake (list '(0 . "LINE") (cons 8 "D-HATCH") (cons 10 '(3171.000000 171.000000 0.000000)) (cons 11 '(3173.000000 169.000000 0.000000))))
(klay "D-HATCH")
(entmake (list '(0 . "LINE") (cons 8 "D-HATCH") (cons 10 '(3172.000000 171.000000 0.000000)) (cons 11 '(3174.000000 169.000000 0.000000))))
(klay "D-HATCH")
(entmake (list '(0 . "LINE") (cons 8 "D-HATCH") (cons 10 '(3173.000000 171.000000 0.000000)) (cons 11 '(3175.000000 169.000000 0.000000))))
(klay "D-HATCH")
(entmake (list '(0 . "LINE") (cons 8 "D-HATCH") (cons 10 '(3174.000000 171.000000 0.000000)) (cons 11 '(3176.000000 169.000000 0.000000))))
(klay "D-HATCH")
(entmake (list '(0 . "LINE") (cons 8 "D-HATCH") (cons 10 '(3175.000000 171.000000 0.000000)) (cons 11 '(3177.000000 169.000000 0.000000))))
(klay "D-HATCH")
(entmake (list '(0 . "LINE") (cons 8 "D-HATCH") (cons 10 '(3176.000000 171.000000 0.000000)) (cons 11 '(3178.000000 169.000000 0.000000))))
(klay "D-HATCH")
(entmake (list '(0 . "LINE") (cons 8 "D-HATCH") (cons 10 '(3177.000000 171.000000 0.000000)) (cons 11 '(3179.000000 169.000000 0.000000))))
(klay "D-HATCH")
(entmake (list '(0 . "LINE") (cons 8 "D-HATCH") (cons 10 '(3178.000000 171.000000 0.000000)) (cons 11 '(3180.000000 169.000000 0.000000))))
(klay "D-HATCH")
(entmake (list '(0 . "LINE") (cons 8 "D-HATCH") (cons 10 '(3179.000000 171.000000 0.000000)) (cons 11 '(3181.000000 169.000000 0.000000))))
(klay "D-HATCH")
(entmake (list '(0 . "LINE") (cons 8 "D-HATCH") (cons 10 '(3180.000000 171.000000 0.000000)) (cons 11 '(3182.000000 169.000000 0.000000))))
(klay "D-HATCH")
(entmake (list '(0 . "LINE") (cons 8 "D-HATCH") (cons 10 '(3181.000000 171.000000 0.000000)) (cons 11 '(3183.000000 169.000000 0.000000))))
(klay "D-HATCH")
(entmake (list '(0 . "LINE") (cons 8 "D-HATCH") (cons 10 '(3182.000000 171.000000 0.000000)) (cons 11 '(3184.000000 169.000000 0.000000))))
(klay "D-HATCH")
(entmake (list '(0 . "LINE") (cons 8 "D-HATCH") (cons 10 '(3183.000000 171.000000 0.000000)) (cons 11 '(3185.000000 169.000000 0.000000))))
(klay "D-HATCH")
(entmake (list '(0 . "LINE") (cons 8 "D-HATCH") (cons 10 '(3184.000000 171.000000 0.000000)) (cons 11 '(3185.500000 169.500000 0.000000))))
(klay "D-HATCH")
(entmake (list '(0 . "LINE") (cons 8 "D-HATCH") (cons 10 '(3185.000000 171.000000 0.000000)) (cons 11 '(3185.500000 170.500000 0.000000))))
(klay "D-OUTLINE")
(command "_.RECTANG" '(3160.750000 102.000000 0.000000) '(3184.750000 102.750000 0.000000))
(klay "D-HATCH")
(entmake (list '(0 . "LINE") (cons 8 "D-HATCH") (cons 10 '(3161.000000 102.750000 0.000000)) (cons 11 '(3161.750000 102.000000 0.000000))))
(klay "D-HATCH")
(entmake (list '(0 . "LINE") (cons 8 "D-HATCH") (cons 10 '(3162.000000 102.750000 0.000000)) (cons 11 '(3162.750000 102.000000 0.000000))))
(klay "D-HATCH")
(entmake (list '(0 . "LINE") (cons 8 "D-HATCH") (cons 10 '(3163.000000 102.750000 0.000000)) (cons 11 '(3163.750000 102.000000 0.000000))))
(klay "D-HATCH")
(entmake (list '(0 . "LINE") (cons 8 "D-HATCH") (cons 10 '(3164.000000 102.750000 0.000000)) (cons 11 '(3164.750000 102.000000 0.000000))))
(klay "D-HATCH")
(entmake (list '(0 . "LINE") (cons 8 "D-HATCH") (cons 10 '(3165.000000 102.750000 0.000000)) (cons 11 '(3165.750000 102.000000 0.000000))))
(klay "D-HATCH")
(entmake (list '(0 . "LINE") (cons 8 "D-HATCH") (cons 10 '(3166.000000 102.750000 0.000000)) (cons 11 '(3166.750000 102.000000 0.000000))))
(klay "D-HATCH")
(entmake (list '(0 . "LINE") (cons 8 "D-HATCH") (cons 10 '(3167.000000 102.750000 0.000000)) (cons 11 '(3167.750000 102.000000 0.000000))))
(klay "D-HATCH")
(entmake (list '(0 . "LINE") (cons 8 "D-HATCH") (cons 10 '(3168.000000 102.750000 0.000000)) (cons 11 '(3168.750000 102.000000 0.000000))))
(klay "D-HATCH")
(entmake (list '(0 . "LINE") (cons 8 "D-HATCH") (cons 10 '(3169.000000 102.750000 0.000000)) (cons 11 '(3169.750000 102.000000 0.000000))))
(klay "D-HATCH")
(entmake (list '(0 . "LINE") (cons 8 "D-HATCH") (cons 10 '(3170.000000 102.750000 0.000000)) (cons 11 '(3170.750000 102.000000 0.000000))))
(klay "D-HATCH")
(entmake (list '(0 . "LINE") (cons 8 "D-HATCH") (cons 10 '(3171.000000 102.750000 0.000000)) (cons 11 '(3171.750000 102.000000 0.000000))))
(klay "D-HATCH")
(entmake (list '(0 . "LINE") (cons 8 "D-HATCH") (cons 10 '(3172.000000 102.750000 0.000000)) (cons 11 '(3172.750000 102.000000 0.000000))))
(klay "D-HATCH")
(entmake (list '(0 . "LINE") (cons 8 "D-HATCH") (cons 10 '(3173.000000 102.750000 0.000000)) (cons 11 '(3173.750000 102.000000 0.000000))))
(klay "D-HATCH")
(entmake (list '(0 . "LINE") (cons 8 "D-HATCH") (cons 10 '(3174.000000 102.750000 0.000000)) (cons 11 '(3174.750000 102.000000 0.000000))))
(klay "D-HATCH")
(entmake (list '(0 . "LINE") (cons 8 "D-HATCH") (cons 10 '(3175.000000 102.750000 0.000000)) (cons 11 '(3175.750000 102.000000 0.000000))))
(klay "D-HATCH")
(entmake (list '(0 . "LINE") (cons 8 "D-HATCH") (cons 10 '(3176.000000 102.750000 0.000000)) (cons 11 '(3176.750000 102.000000 0.000000))))
(klay "D-HATCH")
(entmake (list '(0 . "LINE") (cons 8 "D-HATCH") (cons 10 '(3177.000000 102.750000 0.000000)) (cons 11 '(3177.750000 102.000000 0.000000))))
(klay "D-HATCH")
(entmake (list '(0 . "LINE") (cons 8 "D-HATCH") (cons 10 '(3178.000000 102.750000 0.000000)) (cons 11 '(3178.750000 102.000000 0.000000))))
(klay "D-HATCH")
(entmake (list '(0 . "LINE") (cons 8 "D-HATCH") (cons 10 '(3179.000000 102.750000 0.000000)) (cons 11 '(3179.750000 102.000000 0.000000))))
(klay "D-HATCH")
(entmake (list '(0 . "LINE") (cons 8 "D-HATCH") (cons 10 '(3180.000000 102.750000 0.000000)) (cons 11 '(3180.750000 102.000000 0.000000))))
(klay "D-HATCH")
(entmake (list '(0 . "LINE") (cons 8 "D-HATCH") (cons 10 '(3181.000000 102.750000 0.000000)) (cons 11 '(3181.750000 102.000000 0.000000))))
(klay "D-HATCH")
(entmake (list '(0 . "LINE") (cons 8 "D-HATCH") (cons 10 '(3182.000000 102.750000 0.000000)) (cons 11 '(3182.750000 102.000000 0.000000))))
(klay "D-HATCH")
(entmake (list '(0 . "LINE") (cons 8 "D-HATCH") (cons 10 '(3183.000000 102.750000 0.000000)) (cons 11 '(3183.750000 102.000000 0.000000))))
(klay "D-HATCH")
(entmake (list '(0 . "LINE") (cons 8 "D-HATCH") (cons 10 '(3184.000000 102.750000 0.000000)) (cons 11 '(3184.750000 102.000000 0.000000))))
(klay "D-OUTLINE")
(command "_.RECTANG" '(3160.750000 119.000000 0.000000) '(3184.750000 119.750000 0.000000))
(klay "D-HATCH")
(entmake (list '(0 . "LINE") (cons 8 "D-HATCH") (cons 10 '(3161.000000 119.750000 0.000000)) (cons 11 '(3161.750000 119.000000 0.000000))))
(klay "D-HATCH")
(entmake (list '(0 . "LINE") (cons 8 "D-HATCH") (cons 10 '(3162.000000 119.750000 0.000000)) (cons 11 '(3162.750000 119.000000 0.000000))))
(klay "D-HATCH")
(entmake (list '(0 . "LINE") (cons 8 "D-HATCH") (cons 10 '(3163.000000 119.750000 0.000000)) (cons 11 '(3163.750000 119.000000 0.000000))))
(klay "D-HATCH")
(entmake (list '(0 . "LINE") (cons 8 "D-HATCH") (cons 10 '(3164.000000 119.750000 0.000000)) (cons 11 '(3164.750000 119.000000 0.000000))))
(klay "D-HATCH")
(entmake (list '(0 . "LINE") (cons 8 "D-HATCH") (cons 10 '(3165.000000 119.750000 0.000000)) (cons 11 '(3165.750000 119.000000 0.000000))))
(klay "D-HATCH")
(entmake (list '(0 . "LINE") (cons 8 "D-HATCH") (cons 10 '(3166.000000 119.750000 0.000000)) (cons 11 '(3166.750000 119.000000 0.000000))))
(klay "D-HATCH")
(entmake (list '(0 . "LINE") (cons 8 "D-HATCH") (cons 10 '(3167.000000 119.750000 0.000000)) (cons 11 '(3167.750000 119.000000 0.000000))))
(klay "D-HATCH")
(entmake (list '(0 . "LINE") (cons 8 "D-HATCH") (cons 10 '(3168.000000 119.750000 0.000000)) (cons 11 '(3168.750000 119.000000 0.000000))))
(klay "D-HATCH")
(entmake (list '(0 . "LINE") (cons 8 "D-HATCH") (cons 10 '(3169.000000 119.750000 0.000000)) (cons 11 '(3169.750000 119.000000 0.000000))))
(klay "D-HATCH")
(entmake (list '(0 . "LINE") (cons 8 "D-HATCH") (cons 10 '(3170.000000 119.750000 0.000000)) (cons 11 '(3170.750000 119.000000 0.000000))))
(klay "D-HATCH")
(entmake (list '(0 . "LINE") (cons 8 "D-HATCH") (cons 10 '(3171.000000 119.750000 0.000000)) (cons 11 '(3171.750000 119.000000 0.000000))))
(klay "D-HATCH")
(entmake (list '(0 . "LINE") (cons 8 "D-HATCH") (cons 10 '(3172.000000 119.750000 0.000000)) (cons 11 '(3172.750000 119.000000 0.000000))))
(klay "D-HATCH")
(entmake (list '(0 . "LINE") (cons 8 "D-HATCH") (cons 10 '(3173.000000 119.750000 0.000000)) (cons 11 '(3173.750000 119.000000 0.000000))))
(klay "D-HATCH")
(entmake (list '(0 . "LINE") (cons 8 "D-HATCH") (cons 10 '(3174.000000 119.750000 0.000000)) (cons 11 '(3174.750000 119.000000 0.000000))))
(klay "D-HATCH")
(entmake (list '(0 . "LINE") (cons 8 "D-HATCH") (cons 10 '(3175.000000 119.750000 0.000000)) (cons 11 '(3175.750000 119.000000 0.000000))))
(klay "D-HATCH")
(entmake (list '(0 . "LINE") (cons 8 "D-HATCH") (cons 10 '(3176.000000 119.750000 0.000000)) (cons 11 '(3176.750000 119.000000 0.000000))))
(klay "D-HATCH")
(entmake (list '(0 . "LINE") (cons 8 "D-HATCH") (cons 10 '(3177.000000 119.750000 0.000000)) (cons 11 '(3177.750000 119.000000 0.000000))))
(klay "D-HATCH")
(entmake (list '(0 . "LINE") (cons 8 "D-HATCH") (cons 10 '(3178.000000 119.750000 0.000000)) (cons 11 '(3178.750000 119.000000 0.000000))))
(klay "D-HATCH")
(entmake (list '(0 . "LINE") (cons 8 "D-HATCH") (cons 10 '(3179.000000 119.750000 0.000000)) (cons 11 '(3179.750000 119.000000 0.000000))))
(klay "D-HATCH")
(entmake (list '(0 . "LINE") (cons 8 "D-HATCH") (cons 10 '(3180.000000 119.750000 0.000000)) (cons 11 '(3180.750000 119.000000 0.000000))))
(klay "D-HATCH")
(entmake (list '(0 . "LINE") (cons 8 "D-HATCH") (cons 10 '(3181.000000 119.750000 0.000000)) (cons 11 '(3181.750000 119.000000 0.000000))))
(klay "D-HATCH")
(entmake (list '(0 . "LINE") (cons 8 "D-HATCH") (cons 10 '(3182.000000 119.750000 0.000000)) (cons 11 '(3182.750000 119.000000 0.000000))))
(klay "D-HATCH")
(entmake (list '(0 . "LINE") (cons 8 "D-HATCH") (cons 10 '(3183.000000 119.750000 0.000000)) (cons 11 '(3183.750000 119.000000 0.000000))))
(klay "D-HATCH")
(entmake (list '(0 . "LINE") (cons 8 "D-HATCH") (cons 10 '(3184.000000 119.750000 0.000000)) (cons 11 '(3184.750000 119.000000 0.000000))))
(klay "D-OUTLINE")
(command "_.RECTANG" '(3164.500000 84.750000 0.000000) '(3184.200000 85.500000 0.000000))
(klay "D-HATCH")
(entmake (list '(0 . "LINE") (cons 8 "D-HATCH") (cons 10 '(3164.750000 85.500000 0.000000)) (cons 11 '(3165.500000 84.750000 0.000000))))
(klay "D-HATCH")
(entmake (list '(0 . "LINE") (cons 8 "D-HATCH") (cons 10 '(3165.750000 85.500000 0.000000)) (cons 11 '(3166.500000 84.750000 0.000000))))
(klay "D-HATCH")
(entmake (list '(0 . "LINE") (cons 8 "D-HATCH") (cons 10 '(3166.750000 85.500000 0.000000)) (cons 11 '(3167.500000 84.750000 0.000000))))
(klay "D-HATCH")
(entmake (list '(0 . "LINE") (cons 8 "D-HATCH") (cons 10 '(3167.750000 85.500000 0.000000)) (cons 11 '(3168.500000 84.750000 0.000000))))
(klay "D-HATCH")
(entmake (list '(0 . "LINE") (cons 8 "D-HATCH") (cons 10 '(3168.750000 85.500000 0.000000)) (cons 11 '(3169.500000 84.750000 0.000000))))
(klay "D-HATCH")
(entmake (list '(0 . "LINE") (cons 8 "D-HATCH") (cons 10 '(3169.750000 85.500000 0.000000)) (cons 11 '(3170.500000 84.750000 0.000000))))
(klay "D-HATCH")
(entmake (list '(0 . "LINE") (cons 8 "D-HATCH") (cons 10 '(3170.750000 85.500000 0.000000)) (cons 11 '(3171.500000 84.750000 0.000000))))
(klay "D-HATCH")
(entmake (list '(0 . "LINE") (cons 8 "D-HATCH") (cons 10 '(3171.750000 85.500000 0.000000)) (cons 11 '(3172.500000 84.750000 0.000000))))
(klay "D-HATCH")
(entmake (list '(0 . "LINE") (cons 8 "D-HATCH") (cons 10 '(3172.750000 85.500000 0.000000)) (cons 11 '(3173.500000 84.750000 0.000000))))
(klay "D-HATCH")
(entmake (list '(0 . "LINE") (cons 8 "D-HATCH") (cons 10 '(3173.750000 85.500000 0.000000)) (cons 11 '(3174.500000 84.750000 0.000000))))
(klay "D-HATCH")
(entmake (list '(0 . "LINE") (cons 8 "D-HATCH") (cons 10 '(3174.750000 85.500000 0.000000)) (cons 11 '(3175.500000 84.750000 0.000000))))
(klay "D-HATCH")
(entmake (list '(0 . "LINE") (cons 8 "D-HATCH") (cons 10 '(3175.750000 85.500000 0.000000)) (cons 11 '(3176.500000 84.750000 0.000000))))
(klay "D-HATCH")
(entmake (list '(0 . "LINE") (cons 8 "D-HATCH") (cons 10 '(3176.750000 85.500000 0.000000)) (cons 11 '(3177.500000 84.750000 0.000000))))
(klay "D-HATCH")
(entmake (list '(0 . "LINE") (cons 8 "D-HATCH") (cons 10 '(3177.750000 85.500000 0.000000)) (cons 11 '(3178.500000 84.750000 0.000000))))
(klay "D-HATCH")
(entmake (list '(0 . "LINE") (cons 8 "D-HATCH") (cons 10 '(3178.750000 85.500000 0.000000)) (cons 11 '(3179.500000 84.750000 0.000000))))
(klay "D-HATCH")
(entmake (list '(0 . "LINE") (cons 8 "D-HATCH") (cons 10 '(3179.750000 85.500000 0.000000)) (cons 11 '(3180.500000 84.750000 0.000000))))
(klay "D-HATCH")
(entmake (list '(0 . "LINE") (cons 8 "D-HATCH") (cons 10 '(3180.750000 85.500000 0.000000)) (cons 11 '(3181.500000 84.750000 0.000000))))
(klay "D-HATCH")
(entmake (list '(0 . "LINE") (cons 8 "D-HATCH") (cons 10 '(3181.750000 85.500000 0.000000)) (cons 11 '(3182.500000 84.750000 0.000000))))
(klay "D-HATCH")
(entmake (list '(0 . "LINE") (cons 8 "D-HATCH") (cons 10 '(3182.750000 85.500000 0.000000)) (cons 11 '(3183.500000 84.750000 0.000000))))
(klay "D-HATCH")
(entmake (list '(0 . "LINE") (cons 8 "D-HATCH") (cons 10 '(3183.750000 85.500000 0.000000)) (cons 11 '(3184.200000 85.050000 0.000000))))
(klay "D-FINE")
(entmake (list '(0 . "LINE") (cons 8 "D-FINE") (cons 10 '(3164.500000 83.900000 0.000000)) (cons 11 '(3184.200000 83.900000 0.000000))))
(klay "D-OUTLINE")
(command "_.RECTANG" '(3184.750000 83.000000 0.000000) '(3185.500000 134.000000 0.000000))
(klay "D-DIMS")
(command "_.DIMLINEAR" '(3160.000000 63.000000 0.000000) '(3185.500000 63.000000 0.000000) "_H" '(3172.750000 53.000000 0.000000))
(klay "D-TEXT")
(entmake (list '(0 . "TEXT") (cons 8 "D-TEXT") (cons 10 '(3066.000000 136.000000 0.000000)) (cons 40 1.1) (cons 1 "71 CLEAR OPENING") '(7 . "KITCHEN") '(50 . 0.0)))
(klay "D-OUTLINE")
(command "_.RECTANG" '(3045.937500 83.000000 0.000000) '(3046.062500 134.000000 0.000000))
(klay "D-OUTLINE")
(command "_.RECTANG" '(3045.937500 134.000000 0.000000) '(3046.062500 169.000000 0.000000))
(klay "D-FINE")
(command "_.RECTANG" '(3043.860000 105.820000 0.000000) '(3044.140000 111.180000 0.000000))
(klay "D-FINE")
(command "_.RECTANG" '(3047.860000 105.820000 0.000000) '(3048.140000 111.180000 0.000000))
(klay "D-FINE")
(command "_.RECTANG" '(3043.860000 148.820000 0.000000) '(3044.140000 154.180000 0.000000))
(klay "D-FINE")
(command "_.RECTANG" '(3047.860000 148.820000 0.000000) '(3048.140000 154.180000 0.000000))
(klay "D-FINE")
(command "_.RECTANG" '(3081.485000 148.820000 0.000000) '(3081.765000 154.180000 0.000000))
(klay "D-FINE")
(command "_.RECTANG" '(3085.485000 148.820000 0.000000) '(3085.765000 154.180000 0.000000))
(klay "D-FINE")
(command "_.RECTANG" '(3043.320000 79.860000 0.000000) '(3048.680000 80.140000 0.000000))
(klay "D-TITLE")
(entmake (list '(0 . "TEXT") (cons 8 "D-TITLE") (cons 10 '(3160.000000 44.000000 0.000000)) (cons 40 1.5) (cons 1 "PANTRY SECTION") '(7 . "KITCHEN") '(50 . 0.0)))
(klay "D-TEXT")
(entmake (list '(0 . "TEXT") (cons 8 "D-TEXT") (cons 10 '(3160.000000 40.000000 0.000000)) (cons 40 1.15) (cons 1 "1 in. = 1 ft / fixed upper shelves") '(7 . "KITCHEN") '(50 . 0.0)))
(klay "D-TITLE")
(entmake (list '(0 . "TEXT") (cons 8 "D-TITLE") (cons 10 '(3025.000000 39.000000 0.000000)) (cons 40 2) (cons 1 "03  LEFT RUN / COFFEE PANTRY") '(7 . "KITCHEN") '(50 . 0.0)))
(klay "D-TEXT")
(entmake (list '(0 . "TEXT") (cons 8 "D-TEXT") (cons 10 '(3025.000000 35.000000 0.000000)) (cons 40 1.3) (cons 1 "Pantry external 37; pocket partitions provide 30.9 nominal clear width. Lowest tray only pulls out.") '(7 . "KITCHEN") '(50 . 0.0)))
(klay "D-TEXT")
(entmake (list '(0 . "TEXT") (cons 8 "D-TEXT") (cons 10 '(3211.000000 183.000000 0.000000)) (cons 40 1.26) (cons 1 "COFFEE PANTRY") '(7 . "KITCHEN") '(50 . 0.0)))
(klay "D-TEXT")
(entmake (list '(0 . "TEXT") (cons 8 "D-TEXT") (cons 10 '(3211.000000 180.720000 0.000000)) (cons 40 1.26) (cons 1 "Lower drawer 16 above 4 toe.") '(7 . "KITCHEN") '(50 . 0.0)))
(klay "D-TEXT")
(entmake (list '(0 . "TEXT") (cons 8 "D-TEXT") (cons 10 '(3211.000000 178.440000 0.000000)) (cons 40 1.26) (cons 1 "Pocket bay 51 high: 19 / 17 / 15.") '(7 . "KITCHEN") '(50 . 0.0)))
(klay "D-TEXT")
(entmake (list '(0 . "TEXT") (cons 8 "D-TEXT") (cons 10 '(3211.000000 176.160000 0.000000)) (cons 40 1.26) (cons 1 "Upper cabinet 35 + 2 top filler.") '(7 . "KITCHEN") '(50 . 0.0)))
(klay "D-TEXT")
(entmake (list '(0 . "TEXT") (cons 8 "D-TEXT") (cons 10 '(3211.000000 173.880000 0.000000)) (cons 40 1.26) (cons 1 "Upper two shelves fixed.") '(7 . "KITCHEN") '(50 . 0.0)))
(klay "D-TEXT")
(entmake (list '(0 . "TEXT") (cons 8 "D-TEXT") (cons 10 '(3211.000000 171.600000 0.000000)) (cons 40 1.26) (cons 1 "Lowest tray: proposed 500 mm runner.") '(7 . "KITCHEN") '(50 . 0.0)))
(klay "D-TEXT")
(entmake (list '(0 . "TEXT") (cons 8 "D-TEXT") (cons 10 '(3211.000000 169.320000 0.000000)) (cons 40 1.26) (cons 1 "Pocket doors shown closed.") '(7 . "KITCHEN") '(50 . 0.0)))
(klay "D-TEXT")
(entmake (list '(0 . "TEXT") (cons 8 "D-TEXT") (cons 10 '(3211.000000 167.040000 0.000000)) (cons 40 1.26) (cons 1 "") '(7 . "KITCHEN") '(50 . 0.0)))
(klay "D-TEXT")
(entmake (list '(0 . "TEXT") (cons 8 "D-TEXT") (cons 10 '(3211.000000 164.760000 0.000000)) (cons 40 1.26) (cons 1 "FRIDGE CLEARANCE HOLD") '(7 . "KITCHEN") '(50 . 0.0)))
(klay "D-TEXT")
(entmake (list '(0 . "TEXT") (cons 8 "D-TEXT") (cons 10 '(3211.000000 162.480000 0.000000)) (cons 40 1.26) (cons 1 "Bay nominal 36.75 wide.") '(7 . "KITCHEN") '(50 . 0.0)))
(klay "D-TEXT")
(entmake (list '(0 . "TEXT") (cons 8 "D-TEXT") (cons 10 '(3211.000000 160.200000 0.000000)) (cons 40 1.26) (cons 1 "Opening 71 clear per owner red note.") '(7 . "KITCHEN") '(50 . 0.0)))
(klay "D-TEXT")
(entmake (list '(0 . "TEXT") (cons 8 "D-TEXT") (cons 10 '(3211.000000 157.920000 0.000000)) (cons 40 1.26) (cons 1 "Retained LG maximum height 70.25.") '(7 . "KITCHEN") '(50 . 0.0)))
(klay "D-TEXT")
(entmake (list '(0 . "TEXT") (cons 8 "D-TEXT") (cons 10 '(3211.000000 155.640000 0.000000)) (cons 40 1.26) (cons 1 "Only 0.75 nominal allowance above.") '(7 . "KITCHEN") '(50 . 0.0)))
(klay "D-TEXT")
(entmake (list '(0 . "TEXT") (cons 8 "D-TEXT") (cons 10 '(3211.000000 153.360000 0.000000)) (cons 40 1.26) (cons 1 "Ventilation / hinge / service clearance") '(7 . "KITCHEN") '(50 . 0.0)))
(klay "D-TEXT")
(entmake (list '(0 . "TEXT") (cons 8 "D-TEXT") (cons 10 '(3211.000000 151.080000 0.000000)) (cons 40 1.26) (cons 1 "must be checked against actual model.") '(7 . "KITCHEN") '(50 . 0.0)))
(klay "D-TEXT")
(entmake (list '(0 . "TEXT") (cons 8 "D-TEXT") (cons 10 '(3211.000000 148.800000 0.000000)) (cons 40 1.26) (cons 1 "") '(7 . "KITCHEN") '(50 . 0.0)))
(klay "D-TEXT")
(entmake (list '(0 . "TEXT") (cons 8 "D-TEXT") (cons 10 '(3211.000000 146.520000 0.000000)) (cons 40 1.26) (cons 1 "FINISH") '(7 . "KITCHEN") '(50 . 0.0)))
(klay "D-TEXT")
(entmake (list '(0 . "TEXT") (cons 8 "D-TEXT") (cons 10 '(3211.000000 144.240000 0.000000)) (cons 40 1.26) (cons 1 "25.5 finished pantry depth.") '(7 . "KITCHEN") '(50 . 0.0)))
(klay "D-TEXT")
(entmake (list '(0 . "TEXT") (cons 8 "D-TEXT") (cons 10 '(3211.000000 141.960000 0.000000)) (cons 40 1.26) (cons 1 "Adjacent garage wall face flush.") '(7 . "KITCHEN") '(50 . 0.0)))
(klay "D-TEXT")
(entmake (list '(0 . "TEXT") (cons 8 "D-TEXT") (cons 10 '(3211.000000 139.680000 0.000000)) (cons 40 1.26) (cons 1 "Pocket pull on left from room.") '(7 . "KITCHEN") '(50 . 0.0)))
(klay "D-TEXT")
(entmake (list '(0 . "TEXT") (cons 8 "D-TEXT") (cons 10 '(3211.000000 137.400000 0.000000)) (cons 40 1.26) (cons 1 "Slides toward cabinets; see A402.") '(7 . "KITCHEN") '(50 . 0.0)))
(klay "D-TEXT")
(entmake (list '(0 . "TEXT") (cons 8 "D-TEXT") (cons 10 '(3211.000000 135.120000 0.000000)) (cons 40 1.26) (cons 1 "Saba Beige name / code discrepancy:") '(7 . "KITCHEN") '(50 . 0.0)))
(klay "D-TEXT")
(entmake (list '(0 . "TEXT") (cons 8 "D-TEXT") (cons 10 '(3211.000000 132.840000 0.000000)) (cons 40 1.26) (cons 1 "source 996B; named swatch 669B.") '(7 . "KITCHEN") '(50 . 0.0)))
(klay "D-TEXT")
(entmake (list '(0 . "TEXT") (cons 8 "D-TEXT") (cons 10 '(3211.000000 130.560000 0.000000)) (cons 40 1.26) (cons 1 "Physical finish/code confirmation needed.") '(7 . "KITCHEN") '(50 . 0.0)))
(klay "D-TEXT")
(entmake (list '(0 . "TEXT") (cons 8 "D-TEXT") (cons 10 '(3211.000000 128.280000 0.000000)) (cons 40 1.26) (cons 1 "") '(7 . "KITCHEN") '(50 . 0.0)))
(klay "D-TEXT")
(entmake (list '(0 . "TEXT") (cons 8 "D-TEXT") (cons 10 '(3211.000000 126.000000 0.000000)) (cons 40 1.26) (cons 1 "SOURCE") '(7 . "KITCHEN") '(50 . 0.0)))
(klay "D-TEXT")
(entmake (list '(0 . "TEXT") (cons 8 "D-TEXT") (cons 10 '(3211.000000 123.720000 0.000000)) (cons 40 1.26) (cons 1 "Cabinet pp. 1 / 3 / 4; Owner coordination notes.") '(7 . "KITCHEN") '(50 . 0.0)))
(setvar "DIMTXT" 1.26) (setvar "DIMASZ" 0.8999999999999999) (setvar "DIMGAP" 0.48) (setvar "DIMEXO" 0.72) (setvar "DIMEXE" 0.72)
(if (tblsearch "DIMSTYLE" "KITCHEN_1_12") (command "_.-DIMSTYLE" "_S" "KITCHEN_1_12" "_Y") (command "_.-DIMSTYLE" "_S" "KITCHEN_1_12"))
(command "_.-DIMSTYLE" "_R" "KITCHEN_1_12")
(klay "D-TITLE")
(command "_.RECTANG" '(4004.800000 4.800000 0.000000) '(4283.200000 211.200000 0.000000))
(klay "D-TITLE")
(entmake (list '(0 . "LINE") (cons 8 "D-TITLE") (cons 10 '(4004.800000 20.400000 0.000000)) (cons 11 '(4283.200000 20.400000 0.000000))))
(klay "D-TITLE")
(entmake (list '(0 . "TEXT") (cons 8 "D-TITLE") (cons 10 '(4008.400000 9.600000 0.000000)) (cons 40 1.92) (cons 1 "KITCHEN RENOVATION") '(7 . "KITCHEN") '(50 . 0.0)))
(klay "D-TEXT")
(entmake (list '(0 . "TEXT") (cons 8 "D-TEXT") (cons 10 '(4008.400000 6.600000 0.000000)) (cons 40 1.08) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(4183.600000 13.440000 0.000000)) (cons 40 1.6800000000000002) (cons 1 "Island cabinetry and stone") '(7 . "KITCHEN") '(50 . 0.0)))
(klay "D-TEXT")
(entmake (list '(0 . "TEXT") (cons 8 "D-TEXT") (cons 10 '(4183.600000 8.400000 0.000000)) (cons 40 1.1400000000000001) (cons 1 "22 OCT 2026  |  1 in. = 1 ft  |  24 x 18 in.  |  INCHES") '(7 . "KITCHEN") '(50 . 0.0)))
(klay "D-TITLE")
(entmake (list '(0 . "TEXT") (cons 8 "D-TITLE") (cons 10 '(4259.200000 9.000000 0.000000)) (cons 40 4.08) (cons 1 "A401") '(7 . "KITCHEN") '(50 . 0.0)))
(klay "D-TITLE")
(entmake (list '(0 . "TEXT") (cons 8 "D-TITLE") (cons 10 '(4008.400000 205.800000 0.000000)) (cons 40 2.7600000000000002) (cons 1 "ISLAND CABINETRY AND STONE") '(7 . "KITCHEN") '(50 . 0.0)))
(klay "D-TEXT")
(entmake (list '(0 . "TEXT") (cons 8 "D-TEXT") (cons 10 '(4008.400000 202.320000 0.000000)) (cons 40 1.08) (cons 1 "SOURCE COORDINATION / 22 OCT 2026") '(7 . "KITCHEN") '(50 . 0.0)))
(klay "D-OUTLINE")
(command "_.RECTANG" '(4025.000000 132.000000 0.000000) '(4091.000000 168.000000 0.000000))
(klay "D-OUTLINE")
(command "_.RECTANG" '(4025.000000 166.500000 0.000000) '(4091.000000 168.000000 0.000000))
(klay "D-OUTLINE")
(command "_.RECTANG" '(4025.000000 132.000000 0.000000) '(4026.500000 166.500000 0.000000))
(klay "D-OUTLINE")
(command "_.RECTANG" '(4027.250000 136.000000 0.000000) '(4052.250000 166.500000 0.000000))
(klay "D-FINE")
(entmake (list '(0 . "LINE") (cons 8 "D-FINE") (cons 10 '(4027.250000 149.000000 0.000000)) (cons 11 '(4052.250000 149.000000 0.000000))))
(klay "D-FINE")
(entmake (list '(0 . "LINE") (cons 8 "D-FINE") (cons 10 '(4027.250000 157.750000 0.000000)) (cons 11 '(4052.250000 157.750000 0.000000))))
(klay "D-OUTLINE")
(entmake (list '(0 . "LINE") (cons 8 "D-OUTLINE") (cons 10 '(4037.050000 146.000000 0.000000)) (cons 11 '(4042.450000 146.000000 0.000000))))
(klay "D-OUTLINE")
(entmake (list '(0 . "LINE") (cons 8 "D-OUTLINE") (cons 10 '(4037.050000 154.750000 0.000000)) (cons 11 '(4042.450000 154.750000 0.000000))))
(klay "D-OUTLINE")
(entmake (list '(0 . "LINE") (cons 8 "D-OUTLINE") (cons 10 '(4037.050000 163.500000 0.000000)) (cons 11 '(4042.450000 163.500000 0.000000))))
(klay "D-OUTLINE")
(command "_.RECTANG" '(4052.250000 136.000000 0.000000) '(4077.250000 166.500000 0.000000))
(klay "D-FINE")
(entmake (list '(0 . "LINE") (cons 8 "D-FINE") (cons 10 '(4052.250000 149.000000 0.000000)) (cons 11 '(4077.250000 149.000000 0.000000))))
(klay "D-FINE")
(entmake (list '(0 . "LINE") (cons 8 "D-FINE") (cons 10 '(4052.250000 157.750000 0.000000)) (cons 11 '(4077.250000 157.750000 0.000000))))
(klay "D-OUTLINE")
(entmake (list '(0 . "LINE") (cons 8 "D-OUTLINE") (cons 10 '(4062.050000 146.000000 0.000000)) (cons 11 '(4067.450000 146.000000 0.000000))))
(klay "D-OUTLINE")
(entmake (list '(0 . "LINE") (cons 8 "D-OUTLINE") (cons 10 '(4062.050000 154.750000 0.000000)) (cons 11 '(4067.450000 154.750000 0.000000))))
(klay "D-OUTLINE")
(entmake (list '(0 . "LINE") (cons 8 "D-OUTLINE") (cons 10 '(4062.050000 163.500000 0.000000)) (cons 11 '(4067.450000 163.500000 0.000000))))
(klay "D-FINE")
(command "_.RECTANG" '(4078.000000 136.000000 0.000000) '(4090.000000 166.500000 0.000000))
(klay "D-DIMS")
(command "_.DIMLINEAR" '(4025.000000 168.000000 0.000000) '(4091.000000 168.000000 0.000000) "_H" '(4058.000000 177.000000 0.000000))
(klay "D-DIMS")
(command "_.DIMLINEAR" '(4077.000000 132.000000 0.000000) '(4077.000000 136.000000 0.000000) "_V" '(4098.000000 134.000000 0.000000))
(klay "D-DIMS")
(command "_.DIMLINEAR" '(4077.000000 136.000000 0.000000) '(4077.000000 149.000000 0.000000) "_V" '(4098.000000 142.500000 0.000000))
(klay "D-DIMS")
(command "_.DIMLINEAR" '(4077.000000 149.000000 0.000000) '(4077.000000 157.750000 0.000000) "_V" '(4098.000000 153.375000 0.000000))
(klay "D-DIMS")
(command "_.DIMLINEAR" '(4077.000000 157.750000 0.000000) '(4077.000000 166.500000 0.000000) "_V" '(4098.000000 162.125000 0.000000))
(klay "D-FINE")
(entmake (list '(0 . "LINE") (cons 8 "D-FINE") (cons 10 '(4033.000000 142.000000 0.000000)) (cons 11 '(4045.000000 142.000000 0.000000))))
(klay "D-FINE")
(entmake (list '(0 . "LINE") (cons 8 "D-FINE") (cons 10 '(4033.000000 142.000000 0.000000)) (cons 11 '(4035.000000 143.000000 0.000000))))
(klay "D-FINE")
(entmake (list '(0 . "LINE") (cons 8 "D-FINE") (cons 10 '(4033.000000 142.000000 0.000000)) (cons 11 '(4035.000000 141.000000 0.000000))))
(klay "D-FINE")
(entmake (list '(0 . "LINE") (cons 8 "D-FINE") (cons 10 '(4045.000000 142.000000 0.000000)) (cons 11 '(4043.000000 143.000000 0.000000))))
(klay "D-FINE")
(entmake (list '(0 . "LINE") (cons 8 "D-FINE") (cons 10 '(4045.000000 142.000000 0.000000)) (cons 11 '(4043.000000 141.000000 0.000000))))
(klay "D-TITLE")
(entmake (list '(0 . "TEXT") (cons 8 "D-TITLE") (cons 10 '(4025.000000 122.000000 0.000000)) (cons 40 1.8) (cons 1 "04  MAIN DRAWER FACE") '(7 . "KITCHEN") '(50 . 0.0)))
(klay "D-TEXT")
(entmake (list '(0 . "TEXT") (cons 8 "D-TEXT") (cons 10 '(4025.000000 118.000000 0.000000)) (cons 40 1.25) (cons 1 "Six fronts / horizontal grain / two concealed Type B trays") '(7 . "KITCHEN") '(50 . 0.0)))
(klay "D-OUTLINE")
(command "_.RECTANG" '(4025.000000 58.000000 0.000000) '(4091.000000 94.000000 0.000000))
(klay "D-OUTLINE")
(command "_.RECTANG" '(4025.000000 92.500000 0.000000) '(4091.000000 94.000000 0.000000))
(klay "D-OUTLINE")
(command "_.RECTANG" '(4026.000000 58.000000 0.000000) '(4057.750000 92.500000 0.000000))
(klay "D-OUTLINE")
(command "_.RECTANG" '(4057.750000 58.000000 0.000000) '(4089.500000 92.500000 0.000000))
(klay "D-OUTLINE")
(command "_.RECTANG" '(4089.500000 58.000000 0.000000) '(4091.000000 92.500000 0.000000))
(klay "D-TEXT")
(entmake (list '(0 . "TEXT") (cons 8 "D-TEXT") (cons 10 '(4036.000000 76.000000 0.000000)) (cons 40 1.6) (cons 1 "I03") '(7 . "KITCHEN") '(50 . 0.0)))
(klay "D-TEXT")
(entmake (list '(0 . "TEXT") (cons 8 "D-TEXT") (cons 10 '(4065.000000 76.000000 0.000000)) (cons 40 1.3) (cons 1 "LAMINATE") '(7 . "KITCHEN") '(50 . 0.0)))
(klay "D-DIMS")
(command "_.DIMLINEAR" '(4025.000000 58.000000 0.000000) '(4026.000000 58.000000 0.000000) "_H" '(4025.500000 50.000000 0.000000))
(klay "D-DIMS")
(command "_.DIMLINEAR" '(4026.000000 58.000000 0.000000) '(4057.750000 58.000000 0.000000) "_H" '(4041.875000 50.000000 0.000000))
(klay "D-DIMS")
(command "_.DIMLINEAR" '(4057.750000 58.000000 0.000000) '(4089.500000 58.000000 0.000000) "_H" '(4073.625000 50.000000 0.000000))
(klay "D-DIMS")
(command "_.DIMLINEAR" '(4089.500000 58.000000 0.000000) '(4091.000000 58.000000 0.000000) "_H" '(4090.250000 50.000000 0.000000))
(klay "D-TITLE")
(entmake (list '(0 . "TEXT") (cons 8 "D-TITLE") (cons 10 '(4025.000000 39.000000 0.000000)) (cons 40 1.8) (cons 1 "05  SEATING FACE") '(7 . "KITCHEN") '(50 . 0.0)))
(klay "D-TEXT")
(entmake (list '(0 . "TEXT") (cons 8 "D-TEXT") (cons 10 '(4025.000000 35.000000 0.000000)) (cons 40 1.25) (cons 1 "Range at left / single waterfall at living-room end") '(7 . "KITCHEN") '(50 . 0.0)))
(klay "D-OUTLINE")
(command "_.RECTANG" '(4125.000000 132.000000 0.000000) '(4157.000000 168.000000 0.000000))
(klay "D-OUTLINE")
(command "_.RECTANG" '(4125.000000 166.500000 0.000000) '(4157.000000 168.000000 0.000000))
(klay "D-OUTLINE")
(command "_.RECTANG" '(4135.000000 136.000000 0.000000) '(4157.000000 166.500000 0.000000))
(klay "D-FINE")
(command "_.RECTANG" '(4135.750000 136.000000 0.000000) '(4156.250000 136.750000 0.000000))
(klay "D-FINE")
(command "_.RECTANG" '(4136.400000 137.600000 0.000000) '(4155.600000 143.600000 0.000000))
(klay "D-FINE")
(command "_.RECTANG" '(4135.750000 148.000000 0.000000) '(4156.250000 148.750000 0.000000))
(klay "D-FINE")
(command "_.RECTANG" '(4136.400000 149.600000 0.000000) '(4155.600000 154.100000 0.000000))
(klay "D-FINE")
(command "_.RECTANG" '(4135.750000 157.250000 0.000000) '(4156.250000 158.000000 0.000000))
(klay "D-FINE")
(command "_.RECTANG" '(4136.400000 158.850000 0.000000) '(4155.600000 163.350000 0.000000))
(klay "D-DIMS")
(command "_.DIMLINEAR" '(4125.000000 168.000000 0.000000) '(4135.000000 168.000000 0.000000) "_H" '(4130.000000 177.000000 0.000000))
(klay "D-DIMS")
(command "_.DIMLINEAR" '(4135.000000 168.000000 0.000000) '(4157.000000 168.000000 0.000000) "_H" '(4146.000000 177.000000 0.000000))
(klay "D-DIMS")
(command "_.DIMLINEAR" '(4157.000000 132.000000 0.000000) '(4157.000000 136.000000 0.000000) "_V" '(4165.000000 134.000000 0.000000))
(klay "D-DIMS")
(command "_.DIMLINEAR" '(4157.000000 136.000000 0.000000) '(4157.000000 148.000000 0.000000) "_V" '(4165.000000 142.000000 0.000000))
(klay "D-DIMS")
(command "_.DIMLINEAR" '(4157.000000 148.000000 0.000000) '(4157.000000 157.250000 0.000000) "_V" '(4165.000000 152.625000 0.000000))
(klay "D-DIMS")
(command "_.DIMLINEAR" '(4157.000000 157.250000 0.000000) '(4157.000000 166.500000 0.000000) "_V" '(4165.000000 161.875000 0.000000))
(klay "D-TITLE")
(entmake (list '(0 . "TEXT") (cons 8 "D-TITLE") (cons 10 '(4125.000000 122.000000 0.000000)) (cons 40 1.7) (cons 1 "06  RANGE END / GLASS TRAYS") '(7 . "KITCHEN") '(50 . 0.0)))
(klay "D-TEXT")
(entmake (list '(0 . "TEXT") (cons 8 "D-TEXT") (cons 10 '(4125.000000 118.000000 0.000000)) (cons 40 1.2) (cons 1 "Three supported trays; 20.5 clear bay. No waterfall.") '(7 . "KITCHEN") '(50 . 0.0)))
(klay "D-OUTLINE")
(command "_.RECTANG" '(4125.000000 93.527560 0.000000) '(4157.000000 94.000001 0.000000))
(klay "D-HATCH")
(entmake (list '(0 . "LINE") (cons 8 "D-HATCH") (cons 10 '(4125.527559 94.000001 0.000000)) (cons 11 '(4126.000000 93.527560 0.000000))))
(klay "D-HATCH")
(entmake (list '(0 . "LINE") (cons 8 "D-HATCH") (cons 10 '(4126.527559 94.000001 0.000000)) (cons 11 '(4127.000000 93.527560 0.000000))))
(klay "D-HATCH")
(entmake (list '(0 . "LINE") (cons 8 "D-HATCH") (cons 10 '(4127.527559 94.000001 0.000000)) (cons 11 '(4128.000000 93.527560 0.000000))))
(klay "D-HATCH")
(entmake (list '(0 . "LINE") (cons 8 "D-HATCH") (cons 10 '(4128.527559 94.000001 0.000000)) (cons 11 '(4129.000000 93.527560 0.000000))))
(klay "D-HATCH")
(entmake (list '(0 . "LINE") (cons 8 "D-HATCH") (cons 10 '(4129.527559 94.000001 0.000000)) (cons 11 '(4130.000000 93.527560 0.000000))))
(klay "D-HATCH")
(entmake (list '(0 . "LINE") (cons 8 "D-HATCH") (cons 10 '(4130.527559 94.000001 0.000000)) (cons 11 '(4131.000000 93.527560 0.000000))))
(klay "D-HATCH")
(entmake (list '(0 . "LINE") (cons 8 "D-HATCH") (cons 10 '(4131.527559 94.000001 0.000000)) (cons 11 '(4132.000000 93.527560 0.000000))))
(klay "D-HATCH")
(entmake (list '(0 . "LINE") (cons 8 "D-HATCH") (cons 10 '(4132.527559 94.000001 0.000000)) (cons 11 '(4133.000000 93.527560 0.000000))))
(klay "D-HATCH")
(entmake (list '(0 . "LINE") (cons 8 "D-HATCH") (cons 10 '(4133.527559 94.000001 0.000000)) (cons 11 '(4134.000000 93.527560 0.000000))))
(klay "D-HATCH")
(entmake (list '(0 . "LINE") (cons 8 "D-HATCH") (cons 10 '(4134.527559 94.000001 0.000000)) (cons 11 '(4135.000000 93.527560 0.000000))))
(klay "D-HATCH")
(entmake (list '(0 . "LINE") (cons 8 "D-HATCH") (cons 10 '(4135.527559 94.000001 0.000000)) (cons 11 '(4136.000000 93.527560 0.000000))))
(klay "D-HATCH")
(entmake (list '(0 . "LINE") (cons 8 "D-HATCH") (cons 10 '(4136.527559 94.000001 0.000000)) (cons 11 '(4137.000000 93.527560 0.000000))))
(klay "D-HATCH")
(entmake (list '(0 . "LINE") (cons 8 "D-HATCH") (cons 10 '(4137.527559 94.000001 0.000000)) (cons 11 '(4138.000000 93.527560 0.000000))))
(klay "D-HATCH")
(entmake (list '(0 . "LINE") (cons 8 "D-HATCH") (cons 10 '(4138.527559 94.000001 0.000000)) (cons 11 '(4139.000000 93.527560 0.000000))))
(klay "D-HATCH")
(entmake (list '(0 . "LINE") (cons 8 "D-HATCH") (cons 10 '(4139.527559 94.000001 0.000000)) (cons 11 '(4140.000000 93.527560 0.000000))))
(klay "D-HATCH")
(entmake (list '(0 . "LINE") (cons 8 "D-HATCH") (cons 10 '(4140.527559 94.000001 0.000000)) (cons 11 '(4141.000000 93.527560 0.000000))))
(klay "D-HATCH")
(entmake (list '(0 . "LINE") (cons 8 "D-HATCH") (cons 10 '(4141.527559 94.000001 0.000000)) (cons 11 '(4142.000000 93.527560 0.000000))))
(klay "D-HATCH")
(entmake (list '(0 . "LINE") (cons 8 "D-HATCH") (cons 10 '(4142.527559 94.000001 0.000000)) (cons 11 '(4143.000000 93.527560 0.000000))))
(klay "D-HATCH")
(entmake (list '(0 . "LINE") (cons 8 "D-HATCH") (cons 10 '(4143.527559 94.000001 0.000000)) (cons 11 '(4144.000000 93.527560 0.000000))))
(klay "D-HATCH")
(entmake (list '(0 . "LINE") (cons 8 "D-HATCH") (cons 10 '(4144.527559 94.000001 0.000000)) (cons 11 '(4145.000000 93.527560 0.000000))))
(klay "D-HATCH")
(entmake (list '(0 . "LINE") (cons 8 "D-HATCH") (cons 10 '(4145.527559 94.000001 0.000000)) (cons 11 '(4146.000000 93.527560 0.000000))))
(klay "D-HATCH")
(entmake (list '(0 . "LINE") (cons 8 "D-HATCH") (cons 10 '(4146.527559 94.000001 0.000000)) (cons 11 '(4147.000000 93.527560 0.000000))))
(klay "D-HATCH")
(entmake (list '(0 . "LINE") (cons 8 "D-HATCH") (cons 10 '(4147.527559 94.000001 0.000000)) (cons 11 '(4148.000000 93.527560 0.000000))))
(klay "D-HATCH")
(entmake (list '(0 . "LINE") (cons 8 "D-HATCH") (cons 10 '(4148.527559 94.000001 0.000000)) (cons 11 '(4149.000000 93.527560 0.000000))))
(klay "D-HATCH")
(entmake (list '(0 . "LINE") (cons 8 "D-HATCH") (cons 10 '(4149.527559 94.000001 0.000000)) (cons 11 '(4150.000000 93.527560 0.000000))))
(klay "D-HATCH")
(entmake (list '(0 . "LINE") (cons 8 "D-HATCH") (cons 10 '(4150.527559 94.000001 0.000000)) (cons 11 '(4151.000000 93.527560 0.000000))))
(klay "D-HATCH")
(entmake (list '(0 . "LINE") (cons 8 "D-HATCH") (cons 10 '(4151.527559 94.000001 0.000000)) (cons 11 '(4152.000000 93.527560 0.000000))))
(klay "D-HATCH")
(entmake (list '(0 . "LINE") (cons 8 "D-HATCH") (cons 10 '(4152.527559 94.000001 0.000000)) (cons 11 '(4153.000000 93.527560 0.000000))))
(klay "D-HATCH")
(entmake (list '(0 . "LINE") (cons 8 "D-HATCH") (cons 10 '(4153.527559 94.000001 0.000000)) (cons 11 '(4154.000000 93.527560 0.000000))))
(klay "D-HATCH")
(entmake (list '(0 . "LINE") (cons 8 "D-HATCH") (cons 10 '(4154.527559 94.000001 0.000000)) (cons 11 '(4155.000000 93.527560 0.000000))))
(klay "D-HATCH")
(entmake (list '(0 . "LINE") (cons 8 "D-HATCH") (cons 10 '(4155.527559 94.000001 0.000000)) (cons 11 '(4156.000000 93.527560 0.000000))))
(klay "D-HATCH")
(entmake (list '(0 . "LINE") (cons 8 "D-HATCH") (cons 10 '(4156.527559 94.000001 0.000000)) (cons 11 '(4157.000000 93.527560 0.000000))))
(klay "D-OUTLINE")
(command "_.RECTANG" '(4125.000000 92.500000 0.000000) '(4125.472441 93.527560 0.000000))
(klay "D-HATCH")
(entmake (list '(0 . "LINE") (cons 8 "D-HATCH") (cons 10 '(4125.000000 93.500000 0.000000)) (cons 11 '(4125.472441 93.027559 0.000000))))
(klay "D-OUTLINE")
(command "_.RECTANG" '(4125.000000 92.750000 0.000000) '(4156.500000 93.500000 0.000000))
(klay "D-HATCH")
(entmake (list '(0 . "LINE") (cons 8 "D-HATCH") (cons 10 '(4125.250000 93.500000 0.000000)) (cons 11 '(4126.000000 92.750000 0.000000))))
(klay "D-HATCH")
(entmake (list '(0 . "LINE") (cons 8 "D-HATCH") (cons 10 '(4126.250000 93.500000 0.000000)) (cons 11 '(4127.000000 92.750000 0.000000))))
(klay "D-HATCH")
(entmake (list '(0 . "LINE") (cons 8 "D-HATCH") (cons 10 '(4127.250000 93.500000 0.000000)) (cons 11 '(4128.000000 92.750000 0.000000))))
(klay "D-HATCH")
(entmake (list '(0 . "LINE") (cons 8 "D-HATCH") (cons 10 '(4128.250000 93.500000 0.000000)) (cons 11 '(4129.000000 92.750000 0.000000))))
(klay "D-HATCH")
(entmake (list '(0 . "LINE") (cons 8 "D-HATCH") (cons 10 '(4129.250000 93.500000 0.000000)) (cons 11 '(4130.000000 92.750000 0.000000))))
(klay "D-HATCH")
(entmake (list '(0 . "LINE") (cons 8 "D-HATCH") (cons 10 '(4130.250000 93.500000 0.000000)) (cons 11 '(4131.000000 92.750000 0.000000))))
(klay "D-HATCH")
(entmake (list '(0 . "LINE") (cons 8 "D-HATCH") (cons 10 '(4131.250000 93.500000 0.000000)) (cons 11 '(4132.000000 92.750000 0.000000))))
(klay "D-HATCH")
(entmake (list '(0 . "LINE") (cons 8 "D-HATCH") (cons 10 '(4132.250000 93.500000 0.000000)) (cons 11 '(4133.000000 92.750000 0.000000))))
(klay "D-HATCH")
(entmake (list '(0 . "LINE") (cons 8 "D-HATCH") (cons 10 '(4133.250000 93.500000 0.000000)) (cons 11 '(4134.000000 92.750000 0.000000))))
(klay "D-HATCH")
(entmake (list '(0 . "LINE") (cons 8 "D-HATCH") (cons 10 '(4134.250000 93.500000 0.000000)) (cons 11 '(4135.000000 92.750000 0.000000))))
(klay "D-HATCH")
(entmake (list '(0 . "LINE") (cons 8 "D-HATCH") (cons 10 '(4135.250000 93.500000 0.000000)) (cons 11 '(4136.000000 92.750000 0.000000))))
(klay "D-HATCH")
(entmake (list '(0 . "LINE") (cons 8 "D-HATCH") (cons 10 '(4136.250000 93.500000 0.000000)) (cons 11 '(4137.000000 92.750000 0.000000))))
(klay "D-HATCH")
(entmake (list '(0 . "LINE") (cons 8 "D-HATCH") (cons 10 '(4137.250000 93.500000 0.000000)) (cons 11 '(4138.000000 92.750000 0.000000))))
(klay "D-HATCH")
(entmake (list '(0 . "LINE") (cons 8 "D-HATCH") (cons 10 '(4138.250000 93.500000 0.000000)) (cons 11 '(4139.000000 92.750000 0.000000))))
(klay "D-HATCH")
(entmake (list '(0 . "LINE") (cons 8 "D-HATCH") (cons 10 '(4139.250000 93.500000 0.000000)) (cons 11 '(4140.000000 92.750000 0.000000))))
(klay "D-HATCH")
(entmake (list '(0 . "LINE") (cons 8 "D-HATCH") (cons 10 '(4140.250000 93.500000 0.000000)) (cons 11 '(4141.000000 92.750000 0.000000))))
(klay "D-HATCH")
(entmake (list '(0 . "LINE") (cons 8 "D-HATCH") (cons 10 '(4141.250000 93.500000 0.000000)) (cons 11 '(4142.000000 92.750000 0.000000))))
(klay "D-HATCH")
(entmake (list '(0 . "LINE") (cons 8 "D-HATCH") (cons 10 '(4142.250000 93.500000 0.000000)) (cons 11 '(4143.000000 92.750000 0.000000))))
(klay "D-HATCH")
(entmake (list '(0 . "LINE") (cons 8 "D-HATCH") (cons 10 '(4143.250000 93.500000 0.000000)) (cons 11 '(4144.000000 92.750000 0.000000))))
(klay "D-HATCH")
(entmake (list '(0 . "LINE") (cons 8 "D-HATCH") (cons 10 '(4144.250000 93.500000 0.000000)) (cons 11 '(4145.000000 92.750000 0.000000))))
(klay "D-HATCH")
(entmake (list '(0 . "LINE") (cons 8 "D-HATCH") (cons 10 '(4145.250000 93.500000 0.000000)) (cons 11 '(4146.000000 92.750000 0.000000))))
(klay "D-HATCH")
(entmake (list '(0 . "LINE") (cons 8 "D-HATCH") (cons 10 '(4146.250000 93.500000 0.000000)) (cons 11 '(4147.000000 92.750000 0.000000))))
(klay "D-HATCH")
(entmake (list '(0 . "LINE") (cons 8 "D-HATCH") (cons 10 '(4147.250000 93.500000 0.000000)) (cons 11 '(4148.000000 92.750000 0.000000))))
(klay "D-HATCH")
(entmake (list '(0 . "LINE") (cons 8 "D-HATCH") (cons 10 '(4148.250000 93.500000 0.000000)) (cons 11 '(4149.000000 92.750000 0.000000))))
(klay "D-HATCH")
(entmake (list '(0 . "LINE") (cons 8 "D-HATCH") (cons 10 '(4149.250000 93.500000 0.000000)) (cons 11 '(4150.000000 92.750000 0.000000))))
(klay "D-HATCH")
(entmake (list '(0 . "LINE") (cons 8 "D-HATCH") (cons 10 '(4150.250000 93.500000 0.000000)) (cons 11 '(4151.000000 92.750000 0.000000))))
(klay "D-HATCH")
(entmake (list '(0 . "LINE") (cons 8 "D-HATCH") (cons 10 '(4151.250000 93.500000 0.000000)) (cons 11 '(4152.000000 92.750000 0.000000))))
(klay "D-HATCH")
(entmake (list '(0 . "LINE") (cons 8 "D-HATCH") (cons 10 '(4152.250000 93.500000 0.000000)) (cons 11 '(4153.000000 92.750000 0.000000))))
(klay "D-HATCH")
(entmake (list '(0 . "LINE") (cons 8 "D-HATCH") (cons 10 '(4153.250000 93.500000 0.000000)) (cons 11 '(4154.000000 92.750000 0.000000))))
(klay "D-HATCH")
(entmake (list '(0 . "LINE") (cons 8 "D-HATCH") (cons 10 '(4154.250000 93.500000 0.000000)) (cons 11 '(4155.000000 92.750000 0.000000))))
(klay "D-HATCH")
(entmake (list '(0 . "LINE") (cons 8 "D-HATCH") (cons 10 '(4155.250000 93.500000 0.000000)) (cons 11 '(4156.000000 92.750000 0.000000))))
(klay "D-HATCH")
(entmake (list '(0 . "LINE") (cons 8 "D-HATCH") (cons 10 '(4156.250000 93.500000 0.000000)) (cons 11 '(4156.500000 93.250000 0.000000))))
(klay "D-OUTLINE")
(command "_.RECTANG" '(4135.000000 62.000000 0.000000) '(4135.500000 92.500000 0.000000))
(klay "D-HATCH")
(entmake (list '(0 . "LINE") (cons 8 "D-HATCH") (cons 10 '(4135.000000 63.000000 0.000000)) (cons 11 '(4135.500000 62.500000 0.000000))))
(klay "D-HATCH")
(entmake (list '(0 . "LINE") (cons 8 "D-HATCH") (cons 10 '(4135.000000 64.000000 0.000000)) (cons 11 '(4135.500000 63.500000 0.000000))))
(klay "D-HATCH")
(entmake (list '(0 . "LINE") (cons 8 "D-HATCH") (cons 10 '(4135.000000 65.000000 0.000000)) (cons 11 '(4135.500000 64.500000 0.000000))))
(klay "D-HATCH")
(entmake (list '(0 . "LINE") (cons 8 "D-HATCH") (cons 10 '(4135.000000 66.000000 0.000000)) (cons 11 '(4135.500000 65.500000 0.000000))))
(klay "D-HATCH")
(entmake (list '(0 . "LINE") (cons 8 "D-HATCH") (cons 10 '(4135.000000 67.000000 0.000000)) (cons 11 '(4135.500000 66.500000 0.000000))))
(klay "D-HATCH")
(entmake (list '(0 . "LINE") (cons 8 "D-HATCH") (cons 10 '(4135.000000 68.000000 0.000000)) (cons 11 '(4135.500000 67.500000 0.000000))))
(klay "D-HATCH")
(entmake (list '(0 . "LINE") (cons 8 "D-HATCH") (cons 10 '(4135.000000 69.000000 0.000000)) (cons 11 '(4135.500000 68.500000 0.000000))))
(klay "D-HATCH")
(entmake (list '(0 . "LINE") (cons 8 "D-HATCH") (cons 10 '(4135.000000 70.000000 0.000000)) (cons 11 '(4135.500000 69.500000 0.000000))))
(klay "D-HATCH")
(entmake (list '(0 . "LINE") (cons 8 "D-HATCH") (cons 10 '(4135.000000 71.000000 0.000000)) (cons 11 '(4135.500000 70.500000 0.000000))))
(klay "D-HATCH")
(entmake (list '(0 . "LINE") (cons 8 "D-HATCH") (cons 10 '(4135.000000 72.000000 0.000000)) (cons 11 '(4135.500000 71.500000 0.000000))))
(klay "D-HATCH")
(entmake (list '(0 . "LINE") (cons 8 "D-HATCH") (cons 10 '(4135.000000 73.000000 0.000000)) (cons 11 '(4135.500000 72.500000 0.000000))))
(klay "D-HATCH")
(entmake (list '(0 . "LINE") (cons 8 "D-HATCH") (cons 10 '(4135.000000 74.000000 0.000000)) (cons 11 '(4135.500000 73.500000 0.000000))))
(klay "D-HATCH")
(entmake (list '(0 . "LINE") (cons 8 "D-HATCH") (cons 10 '(4135.000000 75.000000 0.000000)) (cons 11 '(4135.500000 74.500000 0.000000))))
(klay "D-HATCH")
(entmake (list '(0 . "LINE") (cons 8 "D-HATCH") (cons 10 '(4135.000000 76.000000 0.000000)) (cons 11 '(4135.500000 75.500000 0.000000))))
(klay "D-HATCH")
(entmake (list '(0 . "LINE") (cons 8 "D-HATCH") (cons 10 '(4135.000000 77.000000 0.000000)) (cons 11 '(4135.500000 76.500000 0.000000))))
(klay "D-HATCH")
(entmake (list '(0 . "LINE") (cons 8 "D-HATCH") (cons 10 '(4135.000000 78.000000 0.000000)) (cons 11 '(4135.500000 77.500000 0.000000))))
(klay "D-HATCH")
(entmake (list '(0 . "LINE") (cons 8 "D-HATCH") (cons 10 '(4135.000000 79.000000 0.000000)) (cons 11 '(4135.500000 78.500000 0.000000))))
(klay "D-HATCH")
(entmake (list '(0 . "LINE") (cons 8 "D-HATCH") (cons 10 '(4135.000000 80.000000 0.000000)) (cons 11 '(4135.500000 79.500000 0.000000))))
(klay "D-HATCH")
(entmake (list '(0 . "LINE") (cons 8 "D-HATCH") (cons 10 '(4135.000000 81.000000 0.000000)) (cons 11 '(4135.500000 80.500000 0.000000))))
(klay "D-HATCH")
(entmake (list '(0 . "LINE") (cons 8 "D-HATCH") (cons 10 '(4135.000000 82.000000 0.000000)) (cons 11 '(4135.500000 81.500000 0.000000))))
(klay "D-HATCH")
(entmake (list '(0 . "LINE") (cons 8 "D-HATCH") (cons 10 '(4135.000000 83.000000 0.000000)) (cons 11 '(4135.500000 82.500000 0.000000))))
(klay "D-HATCH")
(entmake (list '(0 . "LINE") (cons 8 "D-HATCH") (cons 10 '(4135.000000 84.000000 0.000000)) (cons 11 '(4135.500000 83.500000 0.000000))))
(klay "D-HATCH")
(entmake (list '(0 . "LINE") (cons 8 "D-HATCH") (cons 10 '(4135.000000 85.000000 0.000000)) (cons 11 '(4135.500000 84.500000 0.000000))))
(klay "D-HATCH")
(entmake (list '(0 . "LINE") (cons 8 "D-HATCH") (cons 10 '(4135.000000 86.000000 0.000000)) (cons 11 '(4135.500000 85.500000 0.000000))))
(klay "D-HATCH")
(entmake (list '(0 . "LINE") (cons 8 "D-HATCH") (cons 10 '(4135.000000 87.000000 0.000000)) (cons 11 '(4135.500000 86.500000 0.000000))))
(klay "D-HATCH")
(entmake (list '(0 . "LINE") (cons 8 "D-HATCH") (cons 10 '(4135.000000 88.000000 0.000000)) (cons 11 '(4135.500000 87.500000 0.000000))))
(klay "D-HATCH")
(entmake (list '(0 . "LINE") (cons 8 "D-HATCH") (cons 10 '(4135.000000 89.000000 0.000000)) (cons 11 '(4135.500000 88.500000 0.000000))))
(klay "D-HATCH")
(entmake (list '(0 . "LINE") (cons 8 "D-HATCH") (cons 10 '(4135.000000 90.000000 0.000000)) (cons 11 '(4135.500000 89.500000 0.000000))))
(klay "D-HATCH")
(entmake (list '(0 . "LINE") (cons 8 "D-HATCH") (cons 10 '(4135.000000 91.000000 0.000000)) (cons 11 '(4135.500000 90.500000 0.000000))))
(klay "D-HATCH")
(entmake (list '(0 . "LINE") (cons 8 "D-HATCH") (cons 10 '(4135.000000 92.000000 0.000000)) (cons 11 '(4135.500000 91.500000 0.000000))))
(klay "D-OUTLINE")
(command "_.RECTANG" '(4135.750000 62.000000 0.000000) '(4156.250000 62.750000 0.000000))
(klay "D-HATCH")
(entmake (list '(0 . "LINE") (cons 8 "D-HATCH") (cons 10 '(4136.000000 62.750000 0.000000)) (cons 11 '(4136.750000 62.000000 0.000000))))
(klay "D-HATCH")
(entmake (list '(0 . "LINE") (cons 8 "D-HATCH") (cons 10 '(4137.000000 62.750000 0.000000)) (cons 11 '(4137.750000 62.000000 0.000000))))
(klay "D-HATCH")
(entmake (list '(0 . "LINE") (cons 8 "D-HATCH") (cons 10 '(4138.000000 62.750000 0.000000)) (cons 11 '(4138.750000 62.000000 0.000000))))
(klay "D-HATCH")
(entmake (list '(0 . "LINE") (cons 8 "D-HATCH") (cons 10 '(4139.000000 62.750000 0.000000)) (cons 11 '(4139.750000 62.000000 0.000000))))
(klay "D-HATCH")
(entmake (list '(0 . "LINE") (cons 8 "D-HATCH") (cons 10 '(4140.000000 62.750000 0.000000)) (cons 11 '(4140.750000 62.000000 0.000000))))
(klay "D-HATCH")
(entmake (list '(0 . "LINE") (cons 8 "D-HATCH") (cons 10 '(4141.000000 62.750000 0.000000)) (cons 11 '(4141.750000 62.000000 0.000000))))
(klay "D-HATCH")
(entmake (list '(0 . "LINE") (cons 8 "D-HATCH") (cons 10 '(4142.000000 62.750000 0.000000)) (cons 11 '(4142.750000 62.000000 0.000000))))
(klay "D-HATCH")
(entmake (list '(0 . "LINE") (cons 8 "D-HATCH") (cons 10 '(4143.000000 62.750000 0.000000)) (cons 11 '(4143.750000 62.000000 0.000000))))
(klay "D-HATCH")
(entmake (list '(0 . "LINE") (cons 8 "D-HATCH") (cons 10 '(4144.000000 62.750000 0.000000)) (cons 11 '(4144.750000 62.000000 0.000000))))
(klay "D-HATCH")
(entmake (list '(0 . "LINE") (cons 8 "D-HATCH") (cons 10 '(4145.000000 62.750000 0.000000)) (cons 11 '(4145.750000 62.000000 0.000000))))
(klay "D-HATCH")
(entmake (list '(0 . "LINE") (cons 8 "D-HATCH") (cons 10 '(4146.000000 62.750000 0.000000)) (cons 11 '(4146.750000 62.000000 0.000000))))
(klay "D-HATCH")
(entmake (list '(0 . "LINE") (cons 8 "D-HATCH") (cons 10 '(4147.000000 62.750000 0.000000)) (cons 11 '(4147.750000 62.000000 0.000000))))
(klay "D-HATCH")
(entmake (list '(0 . "LINE") (cons 8 "D-HATCH") (cons 10 '(4148.000000 62.750000 0.000000)) (cons 11 '(4148.750000 62.000000 0.000000))))
(klay "D-HATCH")
(entmake (list '(0 . "LINE") (cons 8 "D-HATCH") (cons 10 '(4149.000000 62.750000 0.000000)) (cons 11 '(4149.750000 62.000000 0.000000))))
(klay "D-HATCH")
(entmake (list '(0 . "LINE") (cons 8 "D-HATCH") (cons 10 '(4150.000000 62.750000 0.000000)) (cons 11 '(4150.750000 62.000000 0.000000))))
(klay "D-HATCH")
(entmake (list '(0 . "LINE") (cons 8 "D-HATCH") (cons 10 '(4151.000000 62.750000 0.000000)) (cons 11 '(4151.750000 62.000000 0.000000))))
(klay "D-HATCH")
(entmake (list '(0 . "LINE") (cons 8 "D-HATCH") (cons 10 '(4152.000000 62.750000 0.000000)) (cons 11 '(4152.750000 62.000000 0.000000))))
(klay "D-HATCH")
(entmake (list '(0 . "LINE") (cons 8 "D-HATCH") (cons 10 '(4153.000000 62.750000 0.000000)) (cons 11 '(4153.750000 62.000000 0.000000))))
(klay "D-HATCH")
(entmake (list '(0 . "LINE") (cons 8 "D-HATCH") (cons 10 '(4154.000000 62.750000 0.000000)) (cons 11 '(4154.750000 62.000000 0.000000))))
(klay "D-HATCH")
(entmake (list '(0 . "LINE") (cons 8 "D-HATCH") (cons 10 '(4155.000000 62.750000 0.000000)) (cons 11 '(4155.750000 62.000000 0.000000))))
(klay "D-HATCH")
(entmake (list '(0 . "LINE") (cons 8 "D-HATCH") (cons 10 '(4156.000000 62.750000 0.000000)) (cons 11 '(4156.250000 62.500000 0.000000))))
(klay "D-OUTLINE")
(command "_.RECTANG" '(4138.000000 58.000000 0.000000) '(4155.000000 62.000000 0.000000))
(klay "D-HATCH")
(entmake (list '(0 . "LINE") (cons 8 "D-HATCH") (cons 10 '(4138.000000 59.000000 0.000000)) (cons 11 '(4139.000000 58.000000 0.000000))))
(klay "D-HATCH")
(entmake (list '(0 . "LINE") (cons 8 "D-HATCH") (cons 10 '(4138.000000 60.000000 0.000000)) (cons 11 '(4140.000000 58.000000 0.000000))))
(klay "D-HATCH")
(entmake (list '(0 . "LINE") (cons 8 "D-HATCH") (cons 10 '(4138.000000 61.000000 0.000000)) (cons 11 '(4141.000000 58.000000 0.000000))))
(klay "D-HATCH")
(entmake (list '(0 . "LINE") (cons 8 "D-HATCH") (cons 10 '(4138.000000 62.000000 0.000000)) (cons 11 '(4142.000000 58.000000 0.000000))))
(klay "D-HATCH")
(entmake (list '(0 . "LINE") (cons 8 "D-HATCH") (cons 10 '(4139.000000 62.000000 0.000000)) (cons 11 '(4143.000000 58.000000 0.000000))))
(klay "D-HATCH")
(entmake (list '(0 . "LINE") (cons 8 "D-HATCH") (cons 10 '(4140.000000 62.000000 0.000000)) (cons 11 '(4144.000000 58.000000 0.000000))))
(klay "D-HATCH")
(entmake (list '(0 . "LINE") (cons 8 "D-HATCH") (cons 10 '(4141.000000 62.000000 0.000000)) (cons 11 '(4145.000000 58.000000 0.000000))))
(klay "D-HATCH")
(entmake (list '(0 . "LINE") (cons 8 "D-HATCH") (cons 10 '(4142.000000 62.000000 0.000000)) (cons 11 '(4146.000000 58.000000 0.000000))))
(klay "D-HATCH")
(entmake (list '(0 . "LINE") (cons 8 "D-HATCH") (cons 10 '(4143.000000 62.000000 0.000000)) (cons 11 '(4147.000000 58.000000 0.000000))))
(klay "D-HATCH")
(entmake (list '(0 . "LINE") (cons 8 "D-HATCH") (cons 10 '(4144.000000 62.000000 0.000000)) (cons 11 '(4148.000000 58.000000 0.000000))))
(klay "D-HATCH")
(entmake (list '(0 . "LINE") (cons 8 "D-HATCH") (cons 10 '(4145.000000 62.000000 0.000000)) (cons 11 '(4149.000000 58.000000 0.000000))))
(klay "D-HATCH")
(entmake (list '(0 . "LINE") (cons 8 "D-HATCH") (cons 10 '(4146.000000 62.000000 0.000000)) (cons 11 '(4150.000000 58.000000 0.000000))))
(klay "D-HATCH")
(entmake (list '(0 . "LINE") (cons 8 "D-HATCH") (cons 10 '(4147.000000 62.000000 0.000000)) (cons 11 '(4151.000000 58.000000 0.000000))))
(klay "D-HATCH")
(entmake (list '(0 . "LINE") (cons 8 "D-HATCH") (cons 10 '(4148.000000 62.000000 0.000000)) (cons 11 '(4152.000000 58.000000 0.000000))))
(klay "D-HATCH")
(entmake (list '(0 . "LINE") (cons 8 "D-HATCH") (cons 10 '(4149.000000 62.000000 0.000000)) (cons 11 '(4153.000000 58.000000 0.000000))))
(klay "D-HATCH")
(entmake (list '(0 . "LINE") (cons 8 "D-HATCH") (cons 10 '(4150.000000 62.000000 0.000000)) (cons 11 '(4154.000000 58.000000 0.000000))))
(klay "D-HATCH")
(entmake (list '(0 . "LINE") (cons 8 "D-HATCH") (cons 10 '(4151.000000 62.000000 0.000000)) (cons 11 '(4155.000000 58.000000 0.000000))))
(klay "D-HATCH")
(entmake (list '(0 . "LINE") (cons 8 "D-HATCH") (cons 10 '(4152.000000 62.000000 0.000000)) (cons 11 '(4155.000000 59.000000 0.000000))))
(klay "D-HATCH")
(entmake (list '(0 . "LINE") (cons 8 "D-HATCH") (cons 10 '(4153.000000 62.000000 0.000000)) (cons 11 '(4155.000000 60.000000 0.000000))))
(klay "D-HATCH")
(entmake (list '(0 . "LINE") (cons 8 "D-HATCH") (cons 10 '(4154.000000 62.000000 0.000000)) (cons 11 '(4155.000000 61.000000 0.000000))))
(klay "D-OUTLINE")
(command "_.RECTANG" '(4156.250000 62.062500 0.000000) '(4157.000000 74.937500 0.000000))
(klay "D-HATCH")
(entmake (list '(0 . "LINE") (cons 8 "D-HATCH") (cons 10 '(4156.250000 63.062500 0.000000)) (cons 11 '(4157.000000 62.312500 0.000000))))
(klay "D-HATCH")
(entmake (list '(0 . "LINE") (cons 8 "D-HATCH") (cons 10 '(4156.250000 64.062500 0.000000)) (cons 11 '(4157.000000 63.312500 0.000000))))
(klay "D-HATCH")
(entmake (list '(0 . "LINE") (cons 8 "D-HATCH") (cons 10 '(4156.250000 65.062500 0.000000)) (cons 11 '(4157.000000 64.312500 0.000000))))
(klay "D-HATCH")
(entmake (list '(0 . "LINE") (cons 8 "D-HATCH") (cons 10 '(4156.250000 66.062500 0.000000)) (cons 11 '(4157.000000 65.312500 0.000000))))
(klay "D-HATCH")
(entmake (list '(0 . "LINE") (cons 8 "D-HATCH") (cons 10 '(4156.250000 67.062500 0.000000)) (cons 11 '(4157.000000 66.312500 0.000000))))
(klay "D-HATCH")
(entmake (list '(0 . "LINE") (cons 8 "D-HATCH") (cons 10 '(4156.250000 68.062500 0.000000)) (cons 11 '(4157.000000 67.312500 0.000000))))
(klay "D-HATCH")
(entmake (list '(0 . "LINE") (cons 8 "D-HATCH") (cons 10 '(4156.250000 69.062500 0.000000)) (cons 11 '(4157.000000 68.312500 0.000000))))
(klay "D-HATCH")
(entmake (list '(0 . "LINE") (cons 8 "D-HATCH") (cons 10 '(4156.250000 70.062500 0.000000)) (cons 11 '(4157.000000 69.312500 0.000000))))
(klay "D-HATCH")
(entmake (list '(0 . "LINE") (cons 8 "D-HATCH") (cons 10 '(4156.250000 71.062500 0.000000)) (cons 11 '(4157.000000 70.312500 0.000000))))
(klay "D-HATCH")
(entmake (list '(0 . "LINE") (cons 8 "D-HATCH") (cons 10 '(4156.250000 72.062500 0.000000)) (cons 11 '(4157.000000 71.312500 0.000000))))
(klay "D-HATCH")
(entmake (list '(0 . "LINE") (cons 8 "D-HATCH") (cons 10 '(4156.250000 73.062500 0.000000)) (cons 11 '(4157.000000 72.312500 0.000000))))
(klay "D-HATCH")
(entmake (list '(0 . "LINE") (cons 8 "D-HATCH") (cons 10 '(4156.250000 74.062500 0.000000)) (cons 11 '(4157.000000 73.312500 0.000000))))
(klay "D-HATCH")
(entmake (list '(0 . "LINE") (cons 8 "D-HATCH") (cons 10 '(4156.375000 74.937500 0.000000)) (cons 11 '(4157.000000 74.312500 0.000000))))
(klay "D-OUTLINE")
(command "_.RECTANG" '(4137.000000 63.250000 0.000000) '(4156.000000 63.750000 0.000000))
(klay "D-HATCH")
(entmake (list '(0 . "LINE") (cons 8 "D-HATCH") (cons 10 '(4137.500000 63.750000 0.000000)) (cons 11 '(4138.000000 63.250000 0.000000))))
(klay "D-HATCH")
(entmake (list '(0 . "LINE") (cons 8 "D-HATCH") (cons 10 '(4138.500000 63.750000 0.000000)) (cons 11 '(4139.000000 63.250000 0.000000))))
(klay "D-HATCH")
(entmake (list '(0 . "LINE") (cons 8 "D-HATCH") (cons 10 '(4139.500000 63.750000 0.000000)) (cons 11 '(4140.000000 63.250000 0.000000))))
(klay "D-HATCH")
(entmake (list '(0 . "LINE") (cons 8 "D-HATCH") (cons 10 '(4140.500000 63.750000 0.000000)) (cons 11 '(4141.000000 63.250000 0.000000))))
(klay "D-HATCH")
(entmake (list '(0 . "LINE") (cons 8 "D-HATCH") (cons 10 '(4141.500000 63.750000 0.000000)) (cons 11 '(4142.000000 63.250000 0.000000))))
(klay "D-HATCH")
(entmake (list '(0 . "LINE") (cons 8 "D-HATCH") (cons 10 '(4142.500000 63.750000 0.000000)) (cons 11 '(4143.000000 63.250000 0.000000))))
(klay "D-HATCH")
(entmake (list '(0 . "LINE") (cons 8 "D-HATCH") (cons 10 '(4143.500000 63.750000 0.000000)) (cons 11 '(4144.000000 63.250000 0.000000))))
(klay "D-HATCH")
(entmake (list '(0 . "LINE") (cons 8 "D-HATCH") (cons 10 '(4144.500000 63.750000 0.000000)) (cons 11 '(4145.000000 63.250000 0.000000))))
(klay "D-HATCH")
(entmake (list '(0 . "LINE") (cons 8 "D-HATCH") (cons 10 '(4145.500000 63.750000 0.000000)) (cons 11 '(4146.000000 63.250000 0.000000))))
(klay "D-HATCH")
(entmake (list '(0 . "LINE") (cons 8 "D-HATCH") (cons 10 '(4146.500000 63.750000 0.000000)) (cons 11 '(4147.000000 63.250000 0.000000))))
(klay "D-HATCH")
(entmake (list '(0 . "LINE") (cons 8 "D-HATCH") (cons 10 '(4147.500000 63.750000 0.000000)) (cons 11 '(4148.000000 63.250000 0.000000))))
(klay "D-HATCH")
(entmake (list '(0 . "LINE") (cons 8 "D-HATCH") (cons 10 '(4148.500000 63.750000 0.000000)) (cons 11 '(4149.000000 63.250000 0.000000))))
(klay "D-HATCH")
(entmake (list '(0 . "LINE") (cons 8 "D-HATCH") (cons 10 '(4149.500000 63.750000 0.000000)) (cons 11 '(4150.000000 63.250000 0.000000))))
(klay "D-HATCH")
(entmake (list '(0 . "LINE") (cons 8 "D-HATCH") (cons 10 '(4150.500000 63.750000 0.000000)) (cons 11 '(4151.000000 63.250000 0.000000))))
(klay "D-HATCH")
(entmake (list '(0 . "LINE") (cons 8 "D-HATCH") (cons 10 '(4151.500000 63.750000 0.000000)) (cons 11 '(4152.000000 63.250000 0.000000))))
(klay "D-HATCH")
(entmake (list '(0 . "LINE") (cons 8 "D-HATCH") (cons 10 '(4152.500000 63.750000 0.000000)) (cons 11 '(4153.000000 63.250000 0.000000))))
(klay "D-HATCH")
(entmake (list '(0 . "LINE") (cons 8 "D-HATCH") (cons 10 '(4153.500000 63.750000 0.000000)) (cons 11 '(4154.000000 63.250000 0.000000))))
(klay "D-HATCH")
(entmake (list '(0 . "LINE") (cons 8 "D-HATCH") (cons 10 '(4154.500000 63.750000 0.000000)) (cons 11 '(4155.000000 63.250000 0.000000))))
(klay "D-HATCH")
(entmake (list '(0 . "LINE") (cons 8 "D-HATCH") (cons 10 '(4155.500000 63.750000 0.000000)) (cons 11 '(4156.000000 63.250000 0.000000))))
(klay "D-OUTLINE")
(command "_.RECTANG" '(4137.000000 63.750000 0.000000) '(4137.500000 70.250000 0.000000))
(klay "D-HATCH")
(entmake (list '(0 . "LINE") (cons 8 "D-HATCH") (cons 10 '(4137.000000 64.750000 0.000000)) (cons 11 '(4137.500000 64.250000 0.000000))))
(klay "D-HATCH")
(entmake (list '(0 . "LINE") (cons 8 "D-HATCH") (cons 10 '(4137.000000 65.750000 0.000000)) (cons 11 '(4137.500000 65.250000 0.000000))))
(klay "D-HATCH")
(entmake (list '(0 . "LINE") (cons 8 "D-HATCH") (cons 10 '(4137.000000 66.750000 0.000000)) (cons 11 '(4137.500000 66.250000 0.000000))))
(klay "D-HATCH")
(entmake (list '(0 . "LINE") (cons 8 "D-HATCH") (cons 10 '(4137.000000 67.750000 0.000000)) (cons 11 '(4137.500000 67.250000 0.000000))))
(klay "D-HATCH")
(entmake (list '(0 . "LINE") (cons 8 "D-HATCH") (cons 10 '(4137.000000 68.750000 0.000000)) (cons 11 '(4137.500000 68.250000 0.000000))))
(klay "D-HATCH")
(entmake (list '(0 . "LINE") (cons 8 "D-HATCH") (cons 10 '(4137.000000 69.750000 0.000000)) (cons 11 '(4137.500000 69.250000 0.000000))))
(klay "D-OUTLINE")
(command "_.RECTANG" '(4155.500000 63.750000 0.000000) '(4156.000000 70.250000 0.000000))
(klay "D-HATCH")
(entmake (list '(0 . "LINE") (cons 8 "D-HATCH") (cons 10 '(4155.500000 64.750000 0.000000)) (cons 11 '(4156.000000 64.250000 0.000000))))
(klay "D-HATCH")
(entmake (list '(0 . "LINE") (cons 8 "D-HATCH") (cons 10 '(4155.500000 65.750000 0.000000)) (cons 11 '(4156.000000 65.250000 0.000000))))
(klay "D-HATCH")
(entmake (list '(0 . "LINE") (cons 8 "D-HATCH") (cons 10 '(4155.500000 66.750000 0.000000)) (cons 11 '(4156.000000 66.250000 0.000000))))
(klay "D-HATCH")
(entmake (list '(0 . "LINE") (cons 8 "D-HATCH") (cons 10 '(4155.500000 67.750000 0.000000)) (cons 11 '(4156.000000 67.250000 0.000000))))
(klay "D-HATCH")
(entmake (list '(0 . "LINE") (cons 8 "D-HATCH") (cons 10 '(4155.500000 68.750000 0.000000)) (cons 11 '(4156.000000 68.250000 0.000000))))
(klay "D-HATCH")
(entmake (list '(0 . "LINE") (cons 8 "D-HATCH") (cons 10 '(4155.500000 69.750000 0.000000)) (cons 11 '(4156.000000 69.250000 0.000000))))
(klay "D-HIDDEN")
(entmake (list '(0 . "LINE") (cons 8 "D-HIDDEN") (cons 10 '(4137.000000 62.950000 0.000000)) (cons 11 '(4155.000000 62.950000 0.000000))))
(klay "D-OUTLINE")
(command "_.RECTANG" '(4157.550000 71.860000 0.000000) '(4157.980000 72.140000 0.000000))
(klay "D-OUTLINE")
(command "_.RECTANG" '(4156.250000 75.062500 0.000000) '(4157.000000 83.687500 0.000000))
(klay "D-HATCH")
(entmake (list '(0 . "LINE") (cons 8 "D-HATCH") (cons 10 '(4156.250000 76.062500 0.000000)) (cons 11 '(4157.000000 75.312500 0.000000))))
(klay "D-HATCH")
(entmake (list '(0 . "LINE") (cons 8 "D-HATCH") (cons 10 '(4156.250000 77.062500 0.000000)) (cons 11 '(4157.000000 76.312500 0.000000))))
(klay "D-HATCH")
(entmake (list '(0 . "LINE") (cons 8 "D-HATCH") (cons 10 '(4156.250000 78.062500 0.000000)) (cons 11 '(4157.000000 77.312500 0.000000))))
(klay "D-HATCH")
(entmake (list '(0 . "LINE") (cons 8 "D-HATCH") (cons 10 '(4156.250000 79.062500 0.000000)) (cons 11 '(4157.000000 78.312500 0.000000))))
(klay "D-HATCH")
(entmake (list '(0 . "LINE") (cons 8 "D-HATCH") (cons 10 '(4156.250000 80.062500 0.000000)) (cons 11 '(4157.000000 79.312500 0.000000))))
(klay "D-HATCH")
(entmake (list '(0 . "LINE") (cons 8 "D-HATCH") (cons 10 '(4156.250000 81.062500 0.000000)) (cons 11 '(4157.000000 80.312500 0.000000))))
(klay "D-HATCH")
(entmake (list '(0 . "LINE") (cons 8 "D-HATCH") (cons 10 '(4156.250000 82.062500 0.000000)) (cons 11 '(4157.000000 81.312500 0.000000))))
(klay "D-HATCH")
(entmake (list '(0 . "LINE") (cons 8 "D-HATCH") (cons 10 '(4156.250000 83.062500 0.000000)) (cons 11 '(4157.000000 82.312500 0.000000))))
(klay "D-HATCH")
(entmake (list '(0 . "LINE") (cons 8 "D-HATCH") (cons 10 '(4156.625000 83.687500 0.000000)) (cons 11 '(4157.000000 83.312500 0.000000))))
(klay "D-OUTLINE")
(command "_.RECTANG" '(4137.000000 76.250000 0.000000) '(4156.000000 76.750000 0.000000))
(klay "D-HATCH")
(entmake (list '(0 . "LINE") (cons 8 "D-HATCH") (cons 10 '(4137.500000 76.750000 0.000000)) (cons 11 '(4138.000000 76.250000 0.000000))))
(klay "D-HATCH")
(entmake (list '(0 . "LINE") (cons 8 "D-HATCH") (cons 10 '(4138.500000 76.750000 0.000000)) (cons 11 '(4139.000000 76.250000 0.000000))))
(klay "D-HATCH")
(entmake (list '(0 . "LINE") (cons 8 "D-HATCH") (cons 10 '(4139.500000 76.750000 0.000000)) (cons 11 '(4140.000000 76.250000 0.000000))))
(klay "D-HATCH")
(entmake (list '(0 . "LINE") (cons 8 "D-HATCH") (cons 10 '(4140.500000 76.750000 0.000000)) (cons 11 '(4141.000000 76.250000 0.000000))))
(klay "D-HATCH")
(entmake (list '(0 . "LINE") (cons 8 "D-HATCH") (cons 10 '(4141.500000 76.750000 0.000000)) (cons 11 '(4142.000000 76.250000 0.000000))))
(klay "D-HATCH")
(entmake (list '(0 . "LINE") (cons 8 "D-HATCH") (cons 10 '(4142.500000 76.750000 0.000000)) (cons 11 '(4143.000000 76.250000 0.000000))))
(klay "D-HATCH")
(entmake (list '(0 . "LINE") (cons 8 "D-HATCH") (cons 10 '(4143.500000 76.750000 0.000000)) (cons 11 '(4144.000000 76.250000 0.000000))))
(klay "D-HATCH")
(entmake (list '(0 . "LINE") (cons 8 "D-HATCH") (cons 10 '(4144.500000 76.750000 0.000000)) (cons 11 '(4145.000000 76.250000 0.000000))))
(klay "D-HATCH")
(entmake (list '(0 . "LINE") (cons 8 "D-HATCH") (cons 10 '(4145.500000 76.750000 0.000000)) (cons 11 '(4146.000000 76.250000 0.000000))))
(klay "D-HATCH")
(entmake (list '(0 . "LINE") (cons 8 "D-HATCH") (cons 10 '(4146.500000 76.750000 0.000000)) (cons 11 '(4147.000000 76.250000 0.000000))))
(klay "D-HATCH")
(entmake (list '(0 . "LINE") (cons 8 "D-HATCH") (cons 10 '(4147.500000 76.750000 0.000000)) (cons 11 '(4148.000000 76.250000 0.000000))))
(klay "D-HATCH")
(entmake (list '(0 . "LINE") (cons 8 "D-HATCH") (cons 10 '(4148.500000 76.750000 0.000000)) (cons 11 '(4149.000000 76.250000 0.000000))))
(klay "D-HATCH")
(entmake (list '(0 . "LINE") (cons 8 "D-HATCH") (cons 10 '(4149.500000 76.750000 0.000000)) (cons 11 '(4150.000000 76.250000 0.000000))))
(klay "D-HATCH")
(entmake (list '(0 . "LINE") (cons 8 "D-HATCH") (cons 10 '(4150.500000 76.750000 0.000000)) (cons 11 '(4151.000000 76.250000 0.000000))))
(klay "D-HATCH")
(entmake (list '(0 . "LINE") (cons 8 "D-HATCH") (cons 10 '(4151.500000 76.750000 0.000000)) (cons 11 '(4152.000000 76.250000 0.000000))))
(klay "D-HATCH")
(entmake (list '(0 . "LINE") (cons 8 "D-HATCH") (cons 10 '(4152.500000 76.750000 0.000000)) (cons 11 '(4153.000000 76.250000 0.000000))))
(klay "D-HATCH")
(entmake (list '(0 . "LINE") (cons 8 "D-HATCH") (cons 10 '(4153.500000 76.750000 0.000000)) (cons 11 '(4154.000000 76.250000 0.000000))))
(klay "D-HATCH")
(entmake (list '(0 . "LINE") (cons 8 "D-HATCH") (cons 10 '(4154.500000 76.750000 0.000000)) (cons 11 '(4155.000000 76.250000 0.000000))))
(klay "D-HATCH")
(entmake (list '(0 . "LINE") (cons 8 "D-HATCH") (cons 10 '(4155.500000 76.750000 0.000000)) (cons 11 '(4156.000000 76.250000 0.000000))))
(klay "D-OUTLINE")
(command "_.RECTANG" '(4137.000000 76.750000 0.000000) '(4137.500000 82.500000 0.000000))
(klay "D-HATCH")
(entmake (list '(0 . "LINE") (cons 8 "D-HATCH") (cons 10 '(4137.000000 77.750000 0.000000)) (cons 11 '(4137.500000 77.250000 0.000000))))
(klay "D-HATCH")
(entmake (list '(0 . "LINE") (cons 8 "D-HATCH") (cons 10 '(4137.000000 78.750000 0.000000)) (cons 11 '(4137.500000 78.250000 0.000000))))
(klay "D-HATCH")
(entmake (list '(0 . "LINE") (cons 8 "D-HATCH") (cons 10 '(4137.000000 79.750000 0.000000)) (cons 11 '(4137.500000 79.250000 0.000000))))
(klay "D-HATCH")
(entmake (list '(0 . "LINE") (cons 8 "D-HATCH") (cons 10 '(4137.000000 80.750000 0.000000)) (cons 11 '(4137.500000 80.250000 0.000000))))
(klay "D-HATCH")
(entmake (list '(0 . "LINE") (cons 8 "D-HATCH") (cons 10 '(4137.000000 81.750000 0.000000)) (cons 11 '(4137.500000 81.250000 0.000000))))
(klay "D-HATCH")
(entmake (list '(0 . "LINE") (cons 8 "D-HATCH") (cons 10 '(4137.250000 82.500000 0.000000)) (cons 11 '(4137.500000 82.250000 0.000000))))
(klay "D-OUTLINE")
(command "_.RECTANG" '(4155.500000 76.750000 0.000000) '(4156.000000 82.500000 0.000000))
(klay "D-HATCH")
(entmake (list '(0 . "LINE") (cons 8 "D-HATCH") (cons 10 '(4155.500000 77.750000 0.000000)) (cons 11 '(4156.000000 77.250000 0.000000))))
(klay "D-HATCH")
(entmake (list '(0 . "LINE") (cons 8 "D-HATCH") (cons 10 '(4155.500000 78.750000 0.000000)) (cons 11 '(4156.000000 78.250000 0.000000))))
(klay "D-HATCH")
(entmake (list '(0 . "LINE") (cons 8 "D-HATCH") (cons 10 '(4155.500000 79.750000 0.000000)) (cons 11 '(4156.000000 79.250000 0.000000))))
(klay "D-HATCH")
(entmake (list '(0 . "LINE") (cons 8 "D-HATCH") (cons 10 '(4155.500000 80.750000 0.000000)) (cons 11 '(4156.000000 80.250000 0.000000))))
(klay "D-HATCH")
(entmake (list '(0 . "LINE") (cons 8 "D-HATCH") (cons 10 '(4155.500000 81.750000 0.000000)) (cons 11 '(4156.000000 81.250000 0.000000))))
(klay "D-HATCH")
(entmake (list '(0 . "LINE") (cons 8 "D-HATCH") (cons 10 '(4155.750000 82.500000 0.000000)) (cons 11 '(4156.000000 82.250000 0.000000))))
(klay "D-HIDDEN")
(entmake (list '(0 . "LINE") (cons 8 "D-HIDDEN") (cons 10 '(4137.000000 75.950000 0.000000)) (cons 11 '(4155.000000 75.950000 0.000000))))
(klay "D-OUTLINE")
(command "_.RECTANG" '(4157.550000 80.610000 0.000000) '(4157.980000 80.890000 0.000000))
(klay "D-OUTLINE")
(command "_.RECTANG" '(4156.250000 83.812500 0.000000) '(4157.000000 92.437500 0.000000))
(klay "D-HATCH")
(entmake (list '(0 . "LINE") (cons 8 "D-HATCH") (cons 10 '(4156.250000 84.812500 0.000000)) (cons 11 '(4157.000000 84.062500 0.000000))))
(klay "D-HATCH")
(entmake (list '(0 . "LINE") (cons 8 "D-HATCH") (cons 10 '(4156.250000 85.812500 0.000000)) (cons 11 '(4157.000000 85.062500 0.000000))))
(klay "D-HATCH")
(entmake (list '(0 . "LINE") (cons 8 "D-HATCH") (cons 10 '(4156.250000 86.812500 0.000000)) (cons 11 '(4157.000000 86.062500 0.000000))))
(klay "D-HATCH")
(entmake (list '(0 . "LINE") (cons 8 "D-HATCH") (cons 10 '(4156.250000 87.812500 0.000000)) (cons 11 '(4157.000000 87.062500 0.000000))))
(klay "D-HATCH")
(entmake (list '(0 . "LINE") (cons 8 "D-HATCH") (cons 10 '(4156.250000 88.812500 0.000000)) (cons 11 '(4157.000000 88.062500 0.000000))))
(klay "D-HATCH")
(entmake (list '(0 . "LINE") (cons 8 "D-HATCH") (cons 10 '(4156.250000 89.812500 0.000000)) (cons 11 '(4157.000000 89.062500 0.000000))))
(klay "D-HATCH")
(entmake (list '(0 . "LINE") (cons 8 "D-HATCH") (cons 10 '(4156.250000 90.812500 0.000000)) (cons 11 '(4157.000000 90.062500 0.000000))))
(klay "D-HATCH")
(entmake (list '(0 . "LINE") (cons 8 "D-HATCH") (cons 10 '(4156.250000 91.812500 0.000000)) (cons 11 '(4157.000000 91.062500 0.000000))))
(klay "D-HATCH")
(entmake (list '(0 . "LINE") (cons 8 "D-HATCH") (cons 10 '(4156.625000 92.437500 0.000000)) (cons 11 '(4157.000000 92.062500 0.000000))))
(klay "D-OUTLINE")
(command "_.RECTANG" '(4137.000000 85.000000 0.000000) '(4156.000000 85.500000 0.000000))
(klay "D-HATCH")
(entmake (list '(0 . "LINE") (cons 8 "D-HATCH") (cons 10 '(4137.500000 85.500000 0.000000)) (cons 11 '(4138.000000 85.000000 0.000000))))
(klay "D-HATCH")
(entmake (list '(0 . "LINE") (cons 8 "D-HATCH") (cons 10 '(4138.500000 85.500000 0.000000)) (cons 11 '(4139.000000 85.000000 0.000000))))
(klay "D-HATCH")
(entmake (list '(0 . "LINE") (cons 8 "D-HATCH") (cons 10 '(4139.500000 85.500000 0.000000)) (cons 11 '(4140.000000 85.000000 0.000000))))
(klay "D-HATCH")
(entmake (list '(0 . "LINE") (cons 8 "D-HATCH") (cons 10 '(4140.500000 85.500000 0.000000)) (cons 11 '(4141.000000 85.000000 0.000000))))
(klay "D-HATCH")
(entmake (list '(0 . "LINE") (cons 8 "D-HATCH") (cons 10 '(4141.500000 85.500000 0.000000)) (cons 11 '(4142.000000 85.000000 0.000000))))
(klay "D-HATCH")
(entmake (list '(0 . "LINE") (cons 8 "D-HATCH") (cons 10 '(4142.500000 85.500000 0.000000)) (cons 11 '(4143.000000 85.000000 0.000000))))
(klay "D-HATCH")
(entmake (list '(0 . "LINE") (cons 8 "D-HATCH") (cons 10 '(4143.500000 85.500000 0.000000)) (cons 11 '(4144.000000 85.000000 0.000000))))
(klay "D-HATCH")
(entmake (list '(0 . "LINE") (cons 8 "D-HATCH") (cons 10 '(4144.500000 85.500000 0.000000)) (cons 11 '(4145.000000 85.000000 0.000000))))
(klay "D-HATCH")
(entmake (list '(0 . "LINE") (cons 8 "D-HATCH") (cons 10 '(4145.500000 85.500000 0.000000)) (cons 11 '(4146.000000 85.000000 0.000000))))
(klay "D-HATCH")
(entmake (list '(0 . "LINE") (cons 8 "D-HATCH") (cons 10 '(4146.500000 85.500000 0.000000)) (cons 11 '(4147.000000 85.000000 0.000000))))
(klay "D-HATCH")
(entmake (list '(0 . "LINE") (cons 8 "D-HATCH") (cons 10 '(4147.500000 85.500000 0.000000)) (cons 11 '(4148.000000 85.000000 0.000000))))
(klay "D-HATCH")
(entmake (list '(0 . "LINE") (cons 8 "D-HATCH") (cons 10 '(4148.500000 85.500000 0.000000)) (cons 11 '(4149.000000 85.000000 0.000000))))
(klay "D-HATCH")
(entmake (list '(0 . "LINE") (cons 8 "D-HATCH") (cons 10 '(4149.500000 85.500000 0.000000)) (cons 11 '(4150.000000 85.000000 0.000000))))
(klay "D-HATCH")
(entmake (list '(0 . "LINE") (cons 8 "D-HATCH") (cons 10 '(4150.500000 85.500000 0.000000)) (cons 11 '(4151.000000 85.000000 0.000000))))
(klay "D-HATCH")
(entmake (list '(0 . "LINE") (cons 8 "D-HATCH") (cons 10 '(4151.500000 85.500000 0.000000)) (cons 11 '(4152.000000 85.000000 0.000000))))
(klay "D-HATCH")
(entmake (list '(0 . "LINE") (cons 8 "D-HATCH") (cons 10 '(4152.500000 85.500000 0.000000)) (cons 11 '(4153.000000 85.000000 0.000000))))
(klay "D-HATCH")
(entmake (list '(0 . "LINE") (cons 8 "D-HATCH") (cons 10 '(4153.500000 85.500000 0.000000)) (cons 11 '(4154.000000 85.000000 0.000000))))
(klay "D-HATCH")
(entmake (list '(0 . "LINE") (cons 8 "D-HATCH") (cons 10 '(4154.500000 85.500000 0.000000)) (cons 11 '(4155.000000 85.000000 0.000000))))
(klay "D-HATCH")
(entmake (list '(0 . "LINE") (cons 8 "D-HATCH") (cons 10 '(4155.500000 85.500000 0.000000)) (cons 11 '(4156.000000 85.000000 0.000000))))
(klay "D-OUTLINE")
(command "_.RECTANG" '(4137.000000 85.500000 0.000000) '(4137.500000 91.250000 0.000000))
(klay "D-HATCH")
(entmake (list '(0 . "LINE") (cons 8 "D-HATCH") (cons 10 '(4137.000000 86.500000 0.000000)) (cons 11 '(4137.500000 86.000000 0.000000))))
(klay "D-HATCH")
(entmake (list '(0 . "LINE") (cons 8 "D-HATCH") (cons 10 '(4137.000000 87.500000 0.000000)) (cons 11 '(4137.500000 87.000000 0.000000))))
(klay "D-HATCH")
(entmake (list '(0 . "LINE") (cons 8 "D-HATCH") (cons 10 '(4137.000000 88.500000 0.000000)) (cons 11 '(4137.500000 88.000000 0.000000))))
(klay "D-HATCH")
(entmake (list '(0 . "LINE") (cons 8 "D-HATCH") (cons 10 '(4137.000000 89.500000 0.000000)) (cons 11 '(4137.500000 89.000000 0.000000))))
(klay "D-HATCH")
(entmake (list '(0 . "LINE") (cons 8 "D-HATCH") (cons 10 '(4137.000000 90.500000 0.000000)) (cons 11 '(4137.500000 90.000000 0.000000))))
(klay "D-HATCH")
(entmake (list '(0 . "LINE") (cons 8 "D-HATCH") (cons 10 '(4137.250000 91.250000 0.000000)) (cons 11 '(4137.500000 91.000000 0.000000))))
(klay "D-OUTLINE")
(command "_.RECTANG" '(4155.500000 85.500000 0.000000) '(4156.000000 91.250000 0.000000))
(klay "D-HATCH")
(entmake (list '(0 . "LINE") (cons 8 "D-HATCH") (cons 10 '(4155.500000 86.500000 0.000000)) (cons 11 '(4156.000000 86.000000 0.000000))))
(klay "D-HATCH")
(entmake (list '(0 . "LINE") (cons 8 "D-HATCH") (cons 10 '(4155.500000 87.500000 0.000000)) (cons 11 '(4156.000000 87.000000 0.000000))))
(klay "D-HATCH")
(entmake (list '(0 . "LINE") (cons 8 "D-HATCH") (cons 10 '(4155.500000 88.500000 0.000000)) (cons 11 '(4156.000000 88.000000 0.000000))))
(klay "D-HATCH")
(entmake (list '(0 . "LINE") (cons 8 "D-HATCH") (cons 10 '(4155.500000 89.500000 0.000000)) (cons 11 '(4156.000000 89.000000 0.000000))))
(klay "D-HATCH")
(entmake (list '(0 . "LINE") (cons 8 "D-HATCH") (cons 10 '(4155.500000 90.500000 0.000000)) (cons 11 '(4156.000000 90.000000 0.000000))))
(klay "D-HATCH")
(entmake (list '(0 . "LINE") (cons 8 "D-HATCH") (cons 10 '(4155.750000 91.250000 0.000000)) (cons 11 '(4156.000000 91.000000 0.000000))))
(klay "D-HIDDEN")
(entmake (list '(0 . "LINE") (cons 8 "D-HIDDEN") (cons 10 '(4137.000000 84.700000 0.000000)) (cons 11 '(4155.000000 84.700000 0.000000))))
(klay "D-OUTLINE")
(command "_.RECTANG" '(4157.550000 89.360000 0.000000) '(4157.980000 89.640000 0.000000))
(klay "D-OUTLINE")
(command "_.RECTANG" '(4137.500000 89.000000 0.000000) '(4155.250000 89.500000 0.000000))
(klay "D-HATCH")
(entmake (list '(0 . "LINE") (cons 8 "D-HATCH") (cons 10 '(4138.000000 89.500000 0.000000)) (cons 11 '(4138.500000 89.000000 0.000000))))
(klay "D-HATCH")
(entmake (list '(0 . "LINE") (cons 8 "D-HATCH") (cons 10 '(4139.000000 89.500000 0.000000)) (cons 11 '(4139.500000 89.000000 0.000000))))
(klay "D-HATCH")
(entmake (list '(0 . "LINE") (cons 8 "D-HATCH") (cons 10 '(4140.000000 89.500000 0.000000)) (cons 11 '(4140.500000 89.000000 0.000000))))
(klay "D-HATCH")
(entmake (list '(0 . "LINE") (cons 8 "D-HATCH") (cons 10 '(4141.000000 89.500000 0.000000)) (cons 11 '(4141.500000 89.000000 0.000000))))
(klay "D-HATCH")
(entmake (list '(0 . "LINE") (cons 8 "D-HATCH") (cons 10 '(4142.000000 89.500000 0.000000)) (cons 11 '(4142.500000 89.000000 0.000000))))
(klay "D-HATCH")
(entmake (list '(0 . "LINE") (cons 8 "D-HATCH") (cons 10 '(4143.000000 89.500000 0.000000)) (cons 11 '(4143.500000 89.000000 0.000000))))
(klay "D-HATCH")
(entmake (list '(0 . "LINE") (cons 8 "D-HATCH") (cons 10 '(4144.000000 89.500000 0.000000)) (cons 11 '(4144.500000 89.000000 0.000000))))
(klay "D-HATCH")
(entmake (list '(0 . "LINE") (cons 8 "D-HATCH") (cons 10 '(4145.000000 89.500000 0.000000)) (cons 11 '(4145.500000 89.000000 0.000000))))
(klay "D-HATCH")
(entmake (list '(0 . "LINE") (cons 8 "D-HATCH") (cons 10 '(4146.000000 89.500000 0.000000)) (cons 11 '(4146.500000 89.000000 0.000000))))
(klay "D-HATCH")
(entmake (list '(0 . "LINE") (cons 8 "D-HATCH") (cons 10 '(4147.000000 89.500000 0.000000)) (cons 11 '(4147.500000 89.000000 0.000000))))
(klay "D-HATCH")
(entmake (list '(0 . "LINE") (cons 8 "D-HATCH") (cons 10 '(4148.000000 89.500000 0.000000)) (cons 11 '(4148.500000 89.000000 0.000000))))
(klay "D-HATCH")
(entmake (list '(0 . "LINE") (cons 8 "D-HATCH") (cons 10 '(4149.000000 89.500000 0.000000)) (cons 11 '(4149.500000 89.000000 0.000000))))
(klay "D-HATCH")
(entmake (list '(0 . "LINE") (cons 8 "D-HATCH") (cons 10 '(4150.000000 89.500000 0.000000)) (cons 11 '(4150.500000 89.000000 0.000000))))
(klay "D-HATCH")
(entmake (list '(0 . "LINE") (cons 8 "D-HATCH") (cons 10 '(4151.000000 89.500000 0.000000)) (cons 11 '(4151.500000 89.000000 0.000000))))
(klay "D-HATCH")
(entmake (list '(0 . "LINE") (cons 8 "D-HATCH") (cons 10 '(4152.000000 89.500000 0.000000)) (cons 11 '(4152.500000 89.000000 0.000000))))
(klay "D-HATCH")
(entmake (list '(0 . "LINE") (cons 8 "D-HATCH") (cons 10 '(4153.000000 89.500000 0.000000)) (cons 11 '(4153.500000 89.000000 0.000000))))
(klay "D-HATCH")
(entmake (list '(0 . "LINE") (cons 8 "D-HATCH") (cons 10 '(4154.000000 89.500000 0.000000)) (cons 11 '(4154.500000 89.000000 0.000000))))
(klay "D-HATCH")
(entmake (list '(0 . "LINE") (cons 8 "D-HATCH") (cons 10 '(4155.000000 89.500000 0.000000)) (cons 11 '(4155.250000 89.250000 0.000000))))
(klay "D-OUTLINE")
(command "_.RECTANG" '(4137.500000 89.500000 0.000000) '(4138.000000 91.750000 0.000000))
(klay "D-HATCH")
(entmake (list '(0 . "LINE") (cons 8 "D-HATCH") (cons 10 '(4137.500000 90.500000 0.000000)) (cons 11 '(4138.000000 90.000000 0.000000))))
(klay "D-HATCH")
(entmake (list '(0 . "LINE") (cons 8 "D-HATCH") (cons 10 '(4137.500000 91.500000 0.000000)) (cons 11 '(4138.000000 91.000000 0.000000))))
(klay "D-OUTLINE")
(command "_.RECTANG" '(4154.750000 89.500000 0.000000) '(4155.250000 91.750000 0.000000))
(klay "D-HATCH")
(entmake (list '(0 . "LINE") (cons 8 "D-HATCH") (cons 10 '(4154.750000 90.500000 0.000000)) (cons 11 '(4155.250000 90.000000 0.000000))))
(klay "D-HATCH")
(entmake (list '(0 . "LINE") (cons 8 "D-HATCH") (cons 10 '(4154.750000 91.500000 0.000000)) (cons 11 '(4155.250000 91.000000 0.000000))))
(klay "D-OUTLINE")
(entmake (list '(0 . "CIRCLE") (cons 8 "D-OUTLINE") (cons 10 '(4130.250000 92.650000 0.000000)) (cons 40 0.28)))
(klay "D-FINE")
(entmake (list '(0 . "LINE") (cons 8 "D-FINE") (cons 10 '(4129.850000 92.100000 0.000000)) (cons 11 '(4130.650000 93.200000 0.000000))))
(klay "D-FINE")
(entmake (list '(0 . "LINE") (cons 8 "D-FINE") (cons 10 '(4148.000000 90.000000 0.000000)) (cons 11 '(4169.000000 90.000000 0.000000))))
(klay "D-FINE")
(entmake (list '(0 . "LINE") (cons 8 "D-FINE") (cons 10 '(4169.000000 90.000000 0.000000)) (cons 11 '(4173.000000 90.000000 0.000000))))
(klay "D-TEXT")
(entmake (list '(0 . "TEXT") (cons 8 "D-TEXT") (cons 10 '(4173.900000 89.650000 0.000000)) (cons 40 1.26) (cons 1 "TYPE B") '(7 . "KITCHEN") '(50 . 0.0)))
(klay "D-FINE")
(entmake (list '(0 . "LINE") (cons 8 "D-FINE") (cons 10 '(4151.000000 76.100000 0.000000)) (cons 11 '(4169.000000 79.000000 0.000000))))
(klay "D-FINE")
(entmake (list '(0 . "LINE") (cons 8 "D-FINE") (cons 10 '(4169.000000 79.000000 0.000000)) (cons 11 '(4173.000000 79.000000 0.000000))))
(klay "D-TEXT")
(entmake (list '(0 . "TEXT") (cons 8 "D-TEXT") (cons 10 '(4173.900000 78.650000 0.000000)) (cons 40 1.26) (cons 1 "DRAWER BOX") '(7 . "KITCHEN") '(50 . 0.0)))
(klay "D-FINE")
(entmake (list '(0 . "LINE") (cons 8 "D-FINE") (cons 10 '(4149.000000 75.950000 0.000000)) (cons 11 '(4169.000000 73.000000 0.000000))))
(klay "D-FINE")
(entmake (list '(0 . "LINE") (cons 8 "D-FINE") (cons 10 '(4169.000000 73.000000 0.000000)) (cons 11 '(4173.000000 73.000000 0.000000))))
(klay "D-TEXT")
(entmake (list '(0 . "TEXT") (cons 8 "D-TEXT") (cons 10 '(4173.900000 72.650000 0.000000)) (cons 40 1.26) (cons 1 "RUNNER") '(7 . "KITCHEN") '(50 . 0.0)))
(klay "D-DIMS")
(command "_.DIMLINEAR" '(4157.000000 58.000000 0.000000) '(4157.000000 94.000000 0.000000) "_V" '(4165.000000 76.000000 0.000000))
(klay "D-DIMS")
(command "_.DIMLINEAR" '(4125.000000 94.000000 0.000000) '(4157.000000 94.000000 0.000000) "_H" '(4141.000000 103.000000 0.000000))
(klay "D-DIMS")
(command "_.DIMLINEAR" '(4130.250000 92.500000 0.000000) '(4135.000000 92.500000 0.000000) "_H" '(4132.625000 86.000000 0.000000))
(klay "D-TEXT")
(entmake (list '(0 . "TEXT") (cons 8 "D-TEXT") (cons 10 '(4125.000000 43.000000 0.000000)) (cons 40 1.1) (cons 1 "CUT THROUGH MAIN BANK / D = 100") '(7 . "KITCHEN") '(50 . 0.0)))
(klay "D-TITLE")
(entmake (list '(0 . "TEXT") (cons 8 "D-TITLE") (cons 10 '(4125.000000 39.000000 0.000000)) (cons 40 1.7) (cons 1 "07  TRANSVERSE SECTION") '(7 . "KITCHEN") '(50 . 0.0)))
(klay "D-TEXT")
(entmake (list '(0 . "TEXT") (cons 8 "D-TEXT") (cons 10 '(4125.000000 35.000000 0.000000)) (cons 40 1.2) (cons 1 "LED centre 4.75 from cabinet face below 10 overhang") '(7 . "KITCHEN") '(50 . 0.0)))
(klay "D-TEXT")
(entmake (list '(0 . "TEXT") (cons 8 "D-TEXT") (cons 10 '(4211.000000 183.000000 0.000000)) (cons 40 1.26) (cons 1 "ISLAND DATUMS") '(7 . "KITCHEN") '(50 . 0.0)))
(klay "D-TEXT")
(entmake (list '(0 . "TEXT") (cons 8 "D-TEXT") (cons 10 '(4211.000000 180.720000 0.000000)) (cons 40 1.26) (cons 1 "Top 66 x 32; finished height 36.") '(7 . "KITCHEN") '(50 . 0.0)))
(klay "D-TEXT")
(entmake (list '(0 . "TEXT") (cons 8 "D-TEXT") (cons 10 '(4211.000000 178.440000 0.000000)) (cons 40 1.26) (cons 1 "22 body + 10 seating overhang.") '(7 . "KITCHEN") '(50 . 0.0)))
(klay "D-TEXT")
(entmake (list '(0 . "TEXT") (cons 8 "D-TEXT") (cons 10 '(4211.000000 176.160000 0.000000)) (cons 40 1.26) (cons 1 "1.5 finished edge / 12 mm porcelain.") '(7 . "KITCHEN") '(50 . 0.0)))
(klay "D-TEXT")
(entmake (list '(0 . "TEXT") (cons 8 "D-TEXT") (cons 10 '(4211.000000 173.880000 0.000000)) (cons 40 1.26) (cons 1 "Main bank 50 = 2 x 25.") '(7 . "KITCHEN") '(50 . 0.0)))
(klay "D-TEXT")
(entmake (list '(0 . "TEXT") (cons 8 "D-TEXT") (cons 10 '(4211.000000 171.600000 0.000000)) (cons 40 1.26) (cons 1 "Main rows 13 / 8.75 / 8.75.") '(7 . "KITCHEN") '(50 . 0.0)))
(klay "D-TEXT")
(entmake (list '(0 . "TEXT") (cons 8 "D-TEXT") (cons 10 '(4211.000000 169.320000 0.000000)) (cons 40 1.26) (cons 1 "Type B trays in both top drawers.") '(7 . "KITCHEN") '(50 . 0.0)))
(klay "D-TEXT")
(entmake (list '(0 . "TEXT") (cons 8 "D-TEXT") (cons 10 '(4211.000000 167.040000 0.000000)) (cons 40 1.26) (cons 1 "No internal dividers.") '(7 . "KITCHEN") '(50 . 0.0)))
(klay "D-TEXT")
(entmake (list '(0 . "TEXT") (cons 8 "D-TEXT") (cons 10 '(4211.000000 164.760000 0.000000)) (cons 40 1.26) (cons 1 "") '(7 . "KITCHEN") '(50 . 0.0)))
(klay "D-TEXT")
(entmake (list '(0 . "TEXT") (cons 8 "D-TEXT") (cons 10 '(4211.000000 162.480000 0.000000)) (cons 40 1.26) (cons 1 "END TRAYS") '(7 . "KITCHEN") '(50 . 0.0)))
(klay "D-TEXT")
(entmake (list '(0 . "TEXT") (cons 8 "D-TEXT") (cons 10 '(4211.000000 160.200000 0.000000)) (cons 40 1.26) (cons 1 "Range-end datums:") '(7 . "KITCHEN") '(50 . 0.0)))
(klay "D-TEXT")
(entmake (list '(0 . "TEXT") (cons 8 "D-TEXT") (cons 10 '(4211.000000 157.920000 0.000000)) (cons 40 1.26) (cons 1 "4 / 16 / 25.25 / 34.5.") '(7 . "KITCHEN") '(50 . 0.0)))
(klay "D-TEXT")
(entmake (list '(0 . "TEXT") (cons 8 "D-TEXT") (cons 10 '(4211.000000 155.640000 0.000000)) (cons 40 1.26) (cons 1 "Glass heights: 6 / 4.5 / 4.5.") '(7 . "KITCHEN") '(50 . 0.0)))
(klay "D-TEXT")
(entmake (list '(0 . "TEXT") (cons 8 "D-TEXT") (cons 10 '(4211.000000 153.360000 0.000000)) (cons 40 1.26) (cons 1 "Outer end is the only waterfall.") '(7 . "KITCHEN") '(50 . 0.0)))
(klay "D-TEXT")
(entmake (list '(0 . "TEXT") (cons 8 "D-TEXT") (cons 10 '(4211.000000 151.080000 0.000000)) (cons 40 1.26) (cons 1 "") '(7 . "KITCHEN") '(50 . 0.0)))
(klay "D-TEXT")
(entmake (list '(0 . "TEXT") (cons 8 "D-TEXT") (cons 10 '(4211.000000 148.800000 0.000000)) (cons 40 1.26) (cons 1 "FINISH / SUPPORT") '(7 . "KITCHEN") '(50 . 0.0)))
(klay "D-TEXT")
(entmake (list '(0 . "TEXT") (cons 8 "D-TEXT") (cons 10 '(4211.000000 146.520000 0.000000)) (cons 40 1.26) (cons 1 "I03: 31.75 x 34.5, range half.") '(7 . "KITCHEN") '(50 . 0.0)))
(klay "D-TEXT")
(entmake (list '(0 . "TEXT") (cons 8 "D-TEXT") (cons 10 '(4211.000000 144.240000 0.000000)) (cons 40 1.26) (cons 1 "I03 flush with adjacent laminate.") '(7 . "KITCHEN") '(50 . 0.0)))
(klay "D-TEXT")
(entmake (list '(0 . "TEXT") (cons 8 "D-TEXT") (cons 10 '(4211.000000 141.960000 0.000000)) (cons 40 1.26) (cons 1 "Main fronts horizontal grain.") '(7 . "KITCHEN") '(50 . 0.0)))
(klay "D-TEXT")
(entmake (list '(0 . "TEXT") (cons 8 "D-TEXT") (cons 10 '(4211.000000 139.680000 0.000000)) (cons 40 1.26) (cons 1 "End panel grain vertical.") '(7 . "KITCHEN") '(50 . 0.0)))
(klay "D-TEXT")
(entmake (list '(0 . "TEXT") (cons 8 "D-TEXT") (cons 10 '(4211.000000 137.400000 0.000000)) (cons 40 1.26) (cons 1 "Stone support, adhesive and runners") '(7 . "KITCHEN") '(50 . 0.0)))
(klay "D-TEXT")
(entmake (list '(0 . "TEXT") (cons 8 "D-TEXT") (cons 10 '(4211.000000 135.120000 0.000000)) (cons 40 1.26) (cons 1 "are coordination intent, not ratings.") '(7 . "KITCHEN") '(50 . 0.0)))
(klay "D-TEXT")
(entmake (list '(0 . "TEXT") (cons 8 "D-TEXT") (cons 10 '(4211.000000 132.840000 0.000000)) (cons 40 1.26) (cons 1 "") '(7 . "KITCHEN") '(50 . 0.0)))
(klay "D-TEXT")
(entmake (list '(0 . "TEXT") (cons 8 "D-TEXT") (cons 10 '(4211.000000 130.560000 0.000000)) (cons 40 1.26) (cons 1 "OUTLET HOLD") '(7 . "KITCHEN") '(50 . 0.0)))
(klay "D-TEXT")
(entmake (list '(0 . "TEXT") (cons 8 "D-TEXT") (cons 10 '(4211.000000 128.280000 0.000000)) (cons 40 1.26) (cons 1 "Upper-corner outlet unselected.") '(7 . "KITCHEN") '(50 . 0.0)))
(klay "D-TEXT")
(entmake (list '(0 . "TEXT") (cons 8 "D-TEXT") (cons 10 '(4211.000000 126.000000 0.000000)) (cons 40 1.26) (cons 1 "Confirm box, backing and tray travel") '(7 . "KITCHEN") '(50 . 0.0)))
(klay "D-TEXT")
(entmake (list '(0 . "TEXT") (cons 8 "D-TEXT") (cons 10 '(4211.000000 123.720000 0.000000)) (cons 40 1.26) (cons 1 "before machining any cutout.") '(7 . "KITCHEN") '(50 . 0.0)))
(klay "D-TEXT")
(entmake (list '(0 . "TEXT") (cons 8 "D-TEXT") (cons 10 '(4211.000000 121.440000 0.000000)) (cons 40 1.26) (cons 1 "") '(7 . "KITCHEN") '(50 . 0.0)))
(klay "D-TEXT")
(entmake (list '(0 . "TEXT") (cons 8 "D-TEXT") (cons 10 '(4211.000000 119.160000 0.000000)) (cons 40 1.26) (cons 1 "SOURCE") '(7 . "KITCHEN") '(50 . 0.0)))
(klay "D-TEXT")
(entmake (list '(0 . "TEXT") (cons 8 "D-TEXT") (cons 10 '(4211.000000 116.880000 0.000000)) (cons 40 1.26) (cons 1 "Cabinet pp. 7-9; R9 S06 / S09.") '(7 . "KITCHEN") '(50 . 0.0)))
(setvar "DIMTXT" 0.21) (setvar "DIMASZ" 0.15) (setvar "DIMGAP" 0.08) (setvar "DIMEXO" 0.12) (setvar "DIMEXE" 0.12)
(if (tblsearch "DIMSTYLE" "KITCHEN_1_2") (command "_.-DIMSTYLE" "_S" "KITCHEN_1_2" "_Y") (command "_.-DIMSTYLE" "_S" "KITCHEN_1_2"))
(command "_.-DIMSTYLE" "_R" "KITCHEN_1_2")
(klay "D-TITLE")
(command "_.RECTANG" '(5000.800000 0.800000 0.000000) '(5047.200000 35.200000 0.000000))
(klay "D-TITLE")
(entmake (list '(0 . "LINE") (cons 8 "D-TITLE") (cons 10 '(5000.800000 3.400000 0.000000)) (cons 11 '(5047.200000 3.400000 0.000000))))
(klay "D-TITLE")
(entmake (list '(0 . "TEXT") (cons 8 "D-TITLE") (cons 10 '(5001.400000 1.600000 0.000000)) (cons 40 0.32) (cons 1 "KITCHEN RENOVATION") '(7 . "KITCHEN") '(50 . 0.0)))
(klay "D-TEXT")
(entmake (list '(0 . "TEXT") (cons 8 "D-TEXT") (cons 10 '(5001.400000 1.100000 0.000000)) (cons 40 0.18) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(5030.600000 2.240000 0.000000)) (cons 40 0.28) (cons 1 "Stone junction details") '(7 . "KITCHEN") '(50 . 0.0)))
(klay "D-TEXT")
(entmake (list '(0 . "TEXT") (cons 8 "D-TEXT") (cons 10 '(5030.600000 1.400000 0.000000)) (cons 40 0.19) (cons 1 "22 OCT 2026  |  6 in. = 1 ft  |  24 x 18 in.  |  INCHES") '(7 . "KITCHEN") '(50 . 0.0)))
(klay "D-TITLE")
(entmake (list '(0 . "TEXT") (cons 8 "D-TITLE") (cons 10 '(5043.200000 1.500000 0.000000)) (cons 40 0.68) (cons 1 "A501") '(7 . "KITCHEN") '(50 . 0.0)))
(klay "D-TITLE")
(entmake (list '(0 . "TEXT") (cons 8 "D-TITLE") (cons 10 '(5001.400000 34.300000 0.000000)) (cons 40 0.46) (cons 1 "STONE JUNCTION DETAILS") '(7 . "KITCHEN") '(50 . 0.0)))
(klay "D-TEXT")
(entmake (list '(0 . "TEXT") (cons 8 "D-TEXT") (cons 10 '(5001.400000 33.720000 0.000000)) (cons 40 0.18) (cons 1 "SOURCE COORDINATION / 22 OCT 2026") '(7 . "KITCHEN") '(50 . 0.0)))
(klay "D-OUTLINE")
(command "_.RECTANG" '(5003.000000 28.027559 0.000000) '(5012.000000 28.500000 0.000000))
(klay "D-HATCH")
(entmake (list '(0 . "LINE") (cons 8 "D-HATCH") (cons 10 '(5003.527559 28.500000 0.000000)) (cons 11 '(5004.000000 28.027559 0.000000))))
(klay "D-HATCH")
(entmake (list '(0 . "LINE") (cons 8 "D-HATCH") (cons 10 '(5004.527559 28.500000 0.000000)) (cons 11 '(5005.000000 28.027559 0.000000))))
(klay "D-HATCH")
(entmake (list '(0 . "LINE") (cons 8 "D-HATCH") (cons 10 '(5005.527559 28.500000 0.000000)) (cons 11 '(5006.000000 28.027559 0.000000))))
(klay "D-HATCH")
(entmake (list '(0 . "LINE") (cons 8 "D-HATCH") (cons 10 '(5006.527559 28.500000 0.000000)) (cons 11 '(5007.000000 28.027559 0.000000))))
(klay "D-HATCH")
(entmake (list '(0 . "LINE") (cons 8 "D-HATCH") (cons 10 '(5007.527559 28.500000 0.000000)) (cons 11 '(5008.000000 28.027559 0.000000))))
(klay "D-HATCH")
(entmake (list '(0 . "LINE") (cons 8 "D-HATCH") (cons 10 '(5008.527559 28.500000 0.000000)) (cons 11 '(5009.000000 28.027559 0.000000))))
(klay "D-HATCH")
(entmake (list '(0 . "LINE") (cons 8 "D-HATCH") (cons 10 '(5009.527559 28.500000 0.000000)) (cons 11 '(5010.000000 28.027559 0.000000))))
(klay "D-HATCH")
(entmake (list '(0 . "LINE") (cons 8 "D-HATCH") (cons 10 '(5010.527559 28.500000 0.000000)) (cons 11 '(5011.000000 28.027559 0.000000))))
(klay "D-HATCH")
(entmake (list '(0 . "LINE") (cons 8 "D-HATCH") (cons 10 '(5011.527559 28.500000 0.000000)) (cons 11 '(5012.000000 28.027559 0.000000))))
(klay "D-OUTLINE")
(command "_.RECTANG" '(5003.000000 27.000000 0.000000) '(5003.472441 28.027559 0.000000))
(klay "D-HATCH")
(entmake (list '(0 . "LINE") (cons 8 "D-HATCH") (cons 10 '(5003.000000 28.000000 0.000000)) (cons 11 '(5003.472441 27.527559 0.000000))))
(klay "D-OUTLINE")
(command "_.RECTANG" '(5003.472441 27.280000 0.000000) '(5011.872441 28.030000 0.000000))
(klay "D-HATCH")
(entmake (list '(0 . "LINE") (cons 8 "D-HATCH") (cons 10 '(5003.722441 28.030000 0.000000)) (cons 11 '(5004.472441 27.280000 0.000000))))
(klay "D-HATCH")
(entmake (list '(0 . "LINE") (cons 8 "D-HATCH") (cons 10 '(5004.722441 28.030000 0.000000)) (cons 11 '(5005.472441 27.280000 0.000000))))
(klay "D-HATCH")
(entmake (list '(0 . "LINE") (cons 8 "D-HATCH") (cons 10 '(5005.722441 28.030000 0.000000)) (cons 11 '(5006.472441 27.280000 0.000000))))
(klay "D-HATCH")
(entmake (list '(0 . "LINE") (cons 8 "D-HATCH") (cons 10 '(5006.722441 28.030000 0.000000)) (cons 11 '(5007.472441 27.280000 0.000000))))
(klay "D-HATCH")
(entmake (list '(0 . "LINE") (cons 8 "D-HATCH") (cons 10 '(5007.722441 28.030000 0.000000)) (cons 11 '(5008.472441 27.280000 0.000000))))
(klay "D-HATCH")
(entmake (list '(0 . "LINE") (cons 8 "D-HATCH") (cons 10 '(5008.722441 28.030000 0.000000)) (cons 11 '(5009.472441 27.280000 0.000000))))
(klay "D-HATCH")
(entmake (list '(0 . "LINE") (cons 8 "D-HATCH") (cons 10 '(5009.722441 28.030000 0.000000)) (cons 11 '(5010.472441 27.280000 0.000000))))
(klay "D-HATCH")
(entmake (list '(0 . "LINE") (cons 8 "D-HATCH") (cons 10 '(5010.722441 28.030000 0.000000)) (cons 11 '(5011.472441 27.280000 0.000000))))
(klay "D-HATCH")
(entmake (list '(0 . "LINE") (cons 8 "D-HATCH") (cons 10 '(5011.722441 28.030000 0.000000)) (cons 11 '(5011.872441 27.880000 0.000000))))
(klay "D-FINE")
(entmake (list '(0 . "LINE") (cons 8 "D-FINE") (cons 10 '(5003.000000 28.027559 0.000000)) (cons 11 '(5003.472441 28.500000 0.000000))))
(klay "D-DIMS")
(command "_.DIMLINEAR" '(5003.000000 27.000000 0.000000) '(5003.000000 28.500000 0.000000) "_V" '(5002.000000 27.750000 0.000000))
(klay "D-FINE")
(entmake (list '(0 . "LINE") (cons 8 "D-FINE") (cons 10 '(5010.000000 28.300000 0.000000)) (cons 11 '(5011.000000 30.000000 0.000000))))
(klay "D-FINE")
(entmake (list '(0 . "LINE") (cons 8 "D-FINE") (cons 10 '(5011.000000 30.000000 0.000000)) (cons 11 '(5011.600000 30.000000 0.000000))))
(klay "D-TEXT")
(entmake (list '(0 . "TEXT") (cons 8 "D-TEXT") (cons 10 '(5011.750000 29.941667 0.000000)) (cons 40 0.21) (cons 1 "12 mm FIELD") '(7 . "KITCHEN") '(50 . 0.0)))
(klay "D-FINE")
(entmake (list '(0 . "LINE") (cons 8 "D-FINE") (cons 10 '(5009.000000 27.600000 0.000000)) (cons 11 '(5011.000000 29.000000 0.000000))))
(klay "D-FINE")
(entmake (list '(0 . "LINE") (cons 8 "D-FINE") (cons 10 '(5011.000000 29.000000 0.000000)) (cons 11 '(5011.600000 29.000000 0.000000))))
(klay "D-TEXT")
(entmake (list '(0 . "TEXT") (cons 8 "D-TEXT") (cons 10 '(5011.750000 28.941667 0.000000)) (cons 40 0.21) (cons 1 "SUBSTRATE") '(7 . "KITCHEN") '(50 . 0.0)))
(klay "D-TITLE")
(entmake (list '(0 . "TEXT") (cons 8 "D-TITLE") (cons 10 '(5003.000000 25.700000 0.000000)) (cons 40 0.36) (cons 1 "08  BUILT-UP EDGE") '(7 . "KITCHEN") '(50 . 0.0)))
(klay "D-TEXT")
(entmake (list '(0 . "TEXT") (cons 8 "D-TEXT") (cons 10 '(5003.000000 25.000000 0.000000)) (cons 40 0.21) (cons 1 "12 mm field; 1.5 finished edge.") '(7 . "KITCHEN") '(50 . 0.0)))
(klay "D-TEXT")
(entmake (list '(0 . "TEXT") (cons 8 "D-TEXT") (cons 10 '(5003.000000 24.620000 0.000000)) (cons 40 0.21) (cons 1 "Mitre / substrate / adhesive by fabricator.") '(7 . "KITCHEN") '(50 . 0.0)))
(klay "D-TEXT")
(entmake (list '(0 . "TEXT") (cons 8 "D-TEXT") (cons 10 '(5003.000000 24.240000 0.000000)) (cons 40 0.21) (cons 1 "Use adjacent same-slab edge band.") '(7 . "KITCHEN") '(50 . 0.0)))
(klay "D-OUTLINE")
(command "_.RECTANG" '(5018.000000 28.027559 0.000000) '(5027.000000 28.500000 0.000000))
(klay "D-HATCH")
(entmake (list '(0 . "LINE") (cons 8 "D-HATCH") (cons 10 '(5018.527559 28.500000 0.000000)) (cons 11 '(5019.000000 28.027559 0.000000))))
(klay "D-HATCH")
(entmake (list '(0 . "LINE") (cons 8 "D-HATCH") (cons 10 '(5019.527559 28.500000 0.000000)) (cons 11 '(5020.000000 28.027559 0.000000))))
(klay "D-HATCH")
(entmake (list '(0 . "LINE") (cons 8 "D-HATCH") (cons 10 '(5020.527559 28.500000 0.000000)) (cons 11 '(5021.000000 28.027559 0.000000))))
(klay "D-HATCH")
(entmake (list '(0 . "LINE") (cons 8 "D-HATCH") (cons 10 '(5021.527559 28.500000 0.000000)) (cons 11 '(5022.000000 28.027559 0.000000))))
(klay "D-HATCH")
(entmake (list '(0 . "LINE") (cons 8 "D-HATCH") (cons 10 '(5022.527559 28.500000 0.000000)) (cons 11 '(5023.000000 28.027559 0.000000))))
(klay "D-HATCH")
(entmake (list '(0 . "LINE") (cons 8 "D-HATCH") (cons 10 '(5023.527559 28.500000 0.000000)) (cons 11 '(5024.000000 28.027559 0.000000))))
(klay "D-HATCH")
(entmake (list '(0 . "LINE") (cons 8 "D-HATCH") (cons 10 '(5024.527559 28.500000 0.000000)) (cons 11 '(5025.000000 28.027559 0.000000))))
(klay "D-HATCH")
(entmake (list '(0 . "LINE") (cons 8 "D-HATCH") (cons 10 '(5025.527559 28.500000 0.000000)) (cons 11 '(5026.000000 28.027559 0.000000))))
(klay "D-HATCH")
(entmake (list '(0 . "LINE") (cons 8 "D-HATCH") (cons 10 '(5026.527559 28.500000 0.000000)) (cons 11 '(5027.000000 28.027559 0.000000))))
(klay "D-OUTLINE")
(command "_.RECTANG" '(5026.527559 22.000000 0.000000) '(5027.000000 28.027559 0.000000))
(klay "D-HATCH")
(entmake (list '(0 . "LINE") (cons 8 "D-HATCH") (cons 10 '(5026.527559 23.000000 0.000000)) (cons 11 '(5027.000000 22.527559 0.000000))))
(klay "D-HATCH")
(entmake (list '(0 . "LINE") (cons 8 "D-HATCH") (cons 10 '(5026.527559 24.000000 0.000000)) (cons 11 '(5027.000000 23.527559 0.000000))))
(klay "D-HATCH")
(entmake (list '(0 . "LINE") (cons 8 "D-HATCH") (cons 10 '(5026.527559 25.000000 0.000000)) (cons 11 '(5027.000000 24.527559 0.000000))))
(klay "D-HATCH")
(entmake (list '(0 . "LINE") (cons 8 "D-HATCH") (cons 10 '(5026.527559 26.000000 0.000000)) (cons 11 '(5027.000000 25.527559 0.000000))))
(klay "D-HATCH")
(entmake (list '(0 . "LINE") (cons 8 "D-HATCH") (cons 10 '(5026.527559 27.000000 0.000000)) (cons 11 '(5027.000000 26.527559 0.000000))))
(klay "D-HATCH")
(entmake (list '(0 . "LINE") (cons 8 "D-HATCH") (cons 10 '(5026.527559 28.000000 0.000000)) (cons 11 '(5027.000000 27.527559 0.000000))))
(klay "D-OUTLINE")
(command "_.RECTANG" '(5018.400000 27.250000 0.000000) '(5026.500000 28.000000 0.000000))
(klay "D-HATCH")
(entmake (list '(0 . "LINE") (cons 8 "D-HATCH") (cons 10 '(5018.650000 28.000000 0.000000)) (cons 11 '(5019.400000 27.250000 0.000000))))
(klay "D-HATCH")
(entmake (list '(0 . "LINE") (cons 8 "D-HATCH") (cons 10 '(5019.650000 28.000000 0.000000)) (cons 11 '(5020.400000 27.250000 0.000000))))
(klay "D-HATCH")
(entmake (list '(0 . "LINE") (cons 8 "D-HATCH") (cons 10 '(5020.650000 28.000000 0.000000)) (cons 11 '(5021.400000 27.250000 0.000000))))
(klay "D-HATCH")
(entmake (list '(0 . "LINE") (cons 8 "D-HATCH") (cons 10 '(5021.650000 28.000000 0.000000)) (cons 11 '(5022.400000 27.250000 0.000000))))
(klay "D-HATCH")
(entmake (list '(0 . "LINE") (cons 8 "D-HATCH") (cons 10 '(5022.650000 28.000000 0.000000)) (cons 11 '(5023.400000 27.250000 0.000000))))
(klay "D-HATCH")
(entmake (list '(0 . "LINE") (cons 8 "D-HATCH") (cons 10 '(5023.650000 28.000000 0.000000)) (cons 11 '(5024.400000 27.250000 0.000000))))
(klay "D-HATCH")
(entmake (list '(0 . "LINE") (cons 8 "D-HATCH") (cons 10 '(5024.650000 28.000000 0.000000)) (cons 11 '(5025.400000 27.250000 0.000000))))
(klay "D-HATCH")
(entmake (list '(0 . "LINE") (cons 8 "D-HATCH") (cons 10 '(5025.650000 28.000000 0.000000)) (cons 11 '(5026.400000 27.250000 0.000000))))
(klay "D-OUTLINE")
(command "_.RECTANG" '(5025.500000 22.000000 0.000000) '(5026.500000 27.250000 0.000000))
(klay "D-HATCH")
(entmake (list '(0 . "LINE") (cons 8 "D-HATCH") (cons 10 '(5025.500000 23.000000 0.000000)) (cons 11 '(5026.500000 22.000000 0.000000))))
(klay "D-HATCH")
(entmake (list '(0 . "LINE") (cons 8 "D-HATCH") (cons 10 '(5025.500000 24.000000 0.000000)) (cons 11 '(5026.500000 23.000000 0.000000))))
(klay "D-HATCH")
(entmake (list '(0 . "LINE") (cons 8 "D-HATCH") (cons 10 '(5025.500000 25.000000 0.000000)) (cons 11 '(5026.500000 24.000000 0.000000))))
(klay "D-HATCH")
(entmake (list '(0 . "LINE") (cons 8 "D-HATCH") (cons 10 '(5025.500000 26.000000 0.000000)) (cons 11 '(5026.500000 25.000000 0.000000))))
(klay "D-HATCH")
(entmake (list '(0 . "LINE") (cons 8 "D-HATCH") (cons 10 '(5025.500000 27.000000 0.000000)) (cons 11 '(5026.500000 26.000000 0.000000))))
(klay "D-HATCH")
(entmake (list '(0 . "LINE") (cons 8 "D-HATCH") (cons 10 '(5026.250000 27.250000 0.000000)) (cons 11 '(5026.500000 27.000000 0.000000))))
(klay "D-FINE")
(entmake (list '(0 . "LINE") (cons 8 "D-FINE") (cons 10 '(5026.527559 28.500000 0.000000)) (cons 11 '(5027.000000 28.027559 0.000000))))
(klay "D-DIMS")
(command "_.DIMLINEAR" '(5025.500000 22.000000 0.000000) '(5027.000000 22.000000 0.000000) "_H" '(5026.250000 21.000000 0.000000))
(klay "D-TITLE")
(entmake (list '(0 . "TEXT") (cons 8 "D-TITLE") (cons 10 '(5018.000000 19.700000 0.000000)) (cons 40 0.36) (cons 1 "09  OUTER WATERFALL / J-W") '(7 . "KITCHEN") '(50 . 0.0)))
(klay "D-TEXT")
(entmake (list '(0 . "TEXT") (cons 8 "D-TEXT") (cons 10 '(5018.000000 19.000000 0.000000)) (cons 40 0.21) (cons 1 "One waterfall at living-room end.") '(7 . "KITCHEN") '(50 . 0.0)))
(klay "D-TEXT")
(entmake (list '(0 . "TEXT") (cons 8 "D-TEXT") (cons 10 '(5018.000000 18.620000 0.000000)) (cons 40 0.21) (cons 1 "1.5 finished return envelope.") '(7 . "KITCHEN") '(50 . 0.0)))
(klay "D-TEXT")
(entmake (list '(0 . "TEXT") (cons 8 "D-TEXT") (cons 10 '(5018.000000 18.240000 0.000000)) (cons 40 0.21) (cons 1 "I01 / I02 vein match across mitre.") '(7 . "KITCHEN") '(50 . 0.0)))
(klay "D-OUTLINE")
(command "_.RECTANG" '(5003.000000 10.027559 0.000000) '(5012.000000 10.500000 0.000000))
(klay "D-HATCH")
(entmake (list '(0 . "LINE") (cons 8 "D-HATCH") (cons 10 '(5003.527559 10.500000 0.000000)) (cons 11 '(5004.000000 10.027559 0.000000))))
(klay "D-HATCH")
(entmake (list '(0 . "LINE") (cons 8 "D-HATCH") (cons 10 '(5004.527559 10.500000 0.000000)) (cons 11 '(5005.000000 10.027559 0.000000))))
(klay "D-HATCH")
(entmake (list '(0 . "LINE") (cons 8 "D-HATCH") (cons 10 '(5005.527559 10.500000 0.000000)) (cons 11 '(5006.000000 10.027559 0.000000))))
(klay "D-HATCH")
(entmake (list '(0 . "LINE") (cons 8 "D-HATCH") (cons 10 '(5006.527559 10.500000 0.000000)) (cons 11 '(5007.000000 10.027559 0.000000))))
(klay "D-HATCH")
(entmake (list '(0 . "LINE") (cons 8 "D-HATCH") (cons 10 '(5007.527559 10.500000 0.000000)) (cons 11 '(5008.000000 10.027559 0.000000))))
(klay "D-HATCH")
(entmake (list '(0 . "LINE") (cons 8 "D-HATCH") (cons 10 '(5008.527559 10.500000 0.000000)) (cons 11 '(5009.000000 10.027559 0.000000))))
(klay "D-HATCH")
(entmake (list '(0 . "LINE") (cons 8 "D-HATCH") (cons 10 '(5009.527559 10.500000 0.000000)) (cons 11 '(5010.000000 10.027559 0.000000))))
(klay "D-HATCH")
(entmake (list '(0 . "LINE") (cons 8 "D-HATCH") (cons 10 '(5010.527559 10.500000 0.000000)) (cons 11 '(5011.000000 10.027559 0.000000))))
(klay "D-HATCH")
(entmake (list '(0 . "LINE") (cons 8 "D-HATCH") (cons 10 '(5011.527559 10.500000 0.000000)) (cons 11 '(5012.000000 10.027559 0.000000))))
(klay "D-OUTLINE")
(command "_.RECTANG" '(5011.527559 10.500000 0.000000) '(5012.000000 16.500000 0.000000))
(klay "D-HATCH")
(entmake (list '(0 . "LINE") (cons 8 "D-HATCH") (cons 10 '(5011.527559 11.500000 0.000000)) (cons 11 '(5012.000000 11.027559 0.000000))))
(klay "D-HATCH")
(entmake (list '(0 . "LINE") (cons 8 "D-HATCH") (cons 10 '(5011.527559 12.500000 0.000000)) (cons 11 '(5012.000000 12.027559 0.000000))))
(klay "D-HATCH")
(entmake (list '(0 . "LINE") (cons 8 "D-HATCH") (cons 10 '(5011.527559 13.500000 0.000000)) (cons 11 '(5012.000000 13.027559 0.000000))))
(klay "D-HATCH")
(entmake (list '(0 . "LINE") (cons 8 "D-HATCH") (cons 10 '(5011.527559 14.500000 0.000000)) (cons 11 '(5012.000000 14.027559 0.000000))))
(klay "D-HATCH")
(entmake (list '(0 . "LINE") (cons 8 "D-HATCH") (cons 10 '(5011.527559 15.500000 0.000000)) (cons 11 '(5012.000000 15.027559 0.000000))))
(klay "D-HATCH")
(entmake (list '(0 . "LINE") (cons 8 "D-HATCH") (cons 10 '(5011.527559 16.500000 0.000000)) (cons 11 '(5012.000000 16.027559 0.000000))))
(klay "D-FINE")
(entmake (list '(0 . "LINE") (cons 8 "D-FINE") (cons 10 '(5011.527559 10.500000 0.000000)) (cons 11 '(5012.000000 10.027559 0.000000))))
(klay "D-TITLE")
(entmake (list '(0 . "TEXT") (cons 8 "D-TITLE") (cons 10 '(5003.000000 7.700000 0.000000)) (cons 40 0.36) (cons 1 "10  COUNTER / BACKSPLASH") '(7 . "KITCHEN") '(50 . 0.0)))
(klay "D-TEXT")
(entmake (list '(0 . "TEXT") (cons 8 "D-TEXT") (cons 10 '(5003.000000 7.000000 0.000000)) (cons 40 0.21) (cons 1 "12 mm Statuario at both fields.") '(7 . "KITCHEN") '(50 . 0.0)))
(klay "D-TEXT")
(entmake (list '(0 . "TEXT") (cons 8 "D-TEXT") (cons 10 '(5003.000000 6.620000 0.000000)) (cons 40 0.21) (cons 1 "Mitred inside corner is design intent.") '(7 . "KITCHEN") '(50 . 0.0)))
(klay "D-TEXT")
(entmake (list '(0 . "TEXT") (cons 8 "D-TEXT") (cons 10 '(5003.000000 6.240000 0.000000)) (cons 40 0.21) (cons 1 "Fabricator to confirm joint / movement.") '(7 . "KITCHEN") '(50 . 0.0)))
(klay "D-OUTLINE")
(command "_.RECTANG" '(5018.000000 10.027559 0.000000) '(5022.000000 10.500000 0.000000))
(klay "D-HATCH")
(entmake (list '(0 . "LINE") (cons 8 "D-HATCH") (cons 10 '(5018.527559 10.500000 0.000000)) (cons 11 '(5019.000000 10.027559 0.000000))))
(klay "D-HATCH")
(entmake (list '(0 . "LINE") (cons 8 "D-HATCH") (cons 10 '(5019.527559 10.500000 0.000000)) (cons 11 '(5020.000000 10.027559 0.000000))))
(klay "D-HATCH")
(entmake (list '(0 . "LINE") (cons 8 "D-HATCH") (cons 10 '(5020.527559 10.500000 0.000000)) (cons 11 '(5021.000000 10.027559 0.000000))))
(klay "D-HATCH")
(entmake (list '(0 . "LINE") (cons 8 "D-HATCH") (cons 10 '(5021.527559 10.500000 0.000000)) (cons 11 '(5022.000000 10.027559 0.000000))))
(klay "D-OUTLINE")
(command "_.RECTANG" '(5018.000000 9.000000 0.000000) '(5022.000000 9.947559 0.000000))
(klay "D-HATCH")
(entmake (list '(0 . "LINE") (cons 8 "D-HATCH") (cons 10 '(5018.052441 9.947559 0.000000)) (cons 11 '(5019.000000 9.000000 0.000000))))
(klay "D-HATCH")
(entmake (list '(0 . "LINE") (cons 8 "D-HATCH") (cons 10 '(5019.052441 9.947559 0.000000)) (cons 11 '(5020.000000 9.000000 0.000000))))
(klay "D-HATCH")
(entmake (list '(0 . "LINE") (cons 8 "D-HATCH") (cons 10 '(5020.052441 9.947559 0.000000)) (cons 11 '(5021.000000 9.000000 0.000000))))
(klay "D-HATCH")
(entmake (list '(0 . "LINE") (cons 8 "D-HATCH") (cons 10 '(5021.052441 9.947559 0.000000)) (cons 11 '(5022.000000 9.000000 0.000000))))
(klay "D-OUTLINE")
(command "_.RECTANG" '(5022.100000 9.750000 0.000000) '(5026.100000 10.500000 0.000000))
(klay "D-HATCH")
(entmake (list '(0 . "LINE") (cons 8 "D-HATCH") (cons 10 '(5022.350000 10.500000 0.000000)) (cons 11 '(5023.100000 9.750000 0.000000))))
(klay "D-HATCH")
(entmake (list '(0 . "LINE") (cons 8 "D-HATCH") (cons 10 '(5023.350000 10.500000 0.000000)) (cons 11 '(5024.100000 9.750000 0.000000))))
(klay "D-HATCH")
(entmake (list '(0 . "LINE") (cons 8 "D-HATCH") (cons 10 '(5024.350000 10.500000 0.000000)) (cons 11 '(5025.100000 9.750000 0.000000))))
(klay "D-HATCH")
(entmake (list '(0 . "LINE") (cons 8 "D-HATCH") (cons 10 '(5025.350000 10.500000 0.000000)) (cons 11 '(5026.100000 9.750000 0.000000))))
(klay "D-FINE")
(command "_.RECTANG" '(5022.100000 9.000000 0.000000) '(5026.100000 9.750000 0.000000))
(klay "D-OUTLINE")
(entmake (list '(0 . "LINE") (cons 8 "D-OUTLINE") (cons 10 '(5018.000000 10.500000 0.000000)) (cons 11 '(5026.100000 10.500000 0.000000))))
(klay "D-FINE")
(entmake (list '(0 . "LINE") (cons 8 "D-FINE") (cons 10 '(5020.000000 10.300000 0.000000)) (cons 11 '(5019.000000 12.000000 0.000000))))
(klay "D-FINE")
(entmake (list '(0 . "LINE") (cons 8 "D-FINE") (cons 10 '(5019.000000 12.000000 0.000000)) (cons 11 '(5019.600000 12.000000 0.000000))))
(klay "D-TEXT")
(entmake (list '(0 . "TEXT") (cons 8 "D-TEXT") (cons 10 '(5019.750000 11.941667 0.000000)) (cons 40 0.21) (cons 1 "PORCELAIN") '(7 . "KITCHEN") '(50 . 0.0)))
(klay "D-FINE")
(entmake (list '(0 . "LINE") (cons 8 "D-FINE") (cons 10 '(5024.000000 10.200000 0.000000)) (cons 11 '(5024.000000 11.500000 0.000000))))
(klay "D-FINE")
(entmake (list '(0 . "LINE") (cons 8 "D-FINE") (cons 10 '(5024.000000 11.500000 0.000000)) (cons 11 '(5024.600000 11.500000 0.000000))))
(klay "D-TEXT")
(entmake (list '(0 . "TEXT") (cons 8 "D-TEXT") (cons 10 '(5024.750000 11.441667 0.000000)) (cons 40 0.21) (cons 1 "LAMINATE") '(7 . "KITCHEN") '(50 . 0.0)))
(klay "D-TEXT")
(entmake (list '(0 . "TEXT") (cons 8 "D-TEXT") (cons 10 '(5018.000000 8.400000 0.000000)) (cons 40 0.18) (cons 1 "BOND LAYER / THICKNESS TO SUPPLIER") '(7 . "KITCHEN") '(50 . 0.0)))
(klay "D-TITLE")
(entmake (list '(0 . "TEXT") (cons 8 "D-TITLE") (cons 10 '(5018.000000 7.700000 0.000000)) (cons 40 0.36) (cons 1 "11  FLUSH I03 / LAMINATE") '(7 . "KITCHEN") '(50 . 0.0)))
(klay "D-TEXT")
(entmake (list '(0 . "TEXT") (cons 8 "D-TEXT") (cons 10 '(5018.000000 7.000000 0.000000)) (cons 40 0.21) (cons 1 "Set back backing for stone + adhesive.") '(7 . "KITCHEN") '(50 . 0.0)))
(klay "D-TEXT")
(entmake (list '(0 . "TEXT") (cons 8 "D-TEXT") (cons 10 '(5018.000000 6.620000 0.000000)) (cons 40 0.21) (cons 1 "Match finished face; keep joint clear.") '(7 . "KITCHEN") '(50 . 0.0)))
(klay "D-TEXT")
(entmake (list '(0 . "TEXT") (cons 8 "D-TEXT") (cons 10 '(5018.000000 6.240000 0.000000)) (cons 40 0.21) (cons 1 "Actual adhesive thickness unselected.") '(7 . "KITCHEN") '(50 . 0.0)))
(klay "D-TEXT")
(entmake (list '(0 . "TEXT") (cons 8 "D-TEXT") (cons 10 '(5031.000000 31.000000 0.000000)) (cons 40 0.21) (cons 1 "STONE COORDINATION") '(7 . "KITCHEN") '(50 . 0.0)))
(klay "D-TEXT")
(entmake (list '(0 . "TEXT") (cons 8 "D-TEXT") (cons 10 '(5031.000000 30.620000 0.000000)) (cons 40 0.21) (cons 1 "12 mm Statuario porcelain.") '(7 . "KITCHEN") '(50 . 0.0)))
(klay "D-TEXT")
(entmake (list '(0 . "TEXT") (cons 8 "D-TEXT") (cons 10 '(5031.000000 30.240000 0.000000)) (cons 40 0.21) (cons 1 "All exposed edges finished.") '(7 . "KITCHEN") '(50 . 0.0)))
(klay "D-TEXT")
(entmake (list '(0 . "TEXT") (cons 8 "D-TEXT") (cons 10 '(5031.000000 29.860000 0.000000)) (cons 40 0.21) (cons 1 "Joint widths / fillers by supplier.") '(7 . "KITCHEN") '(50 . 0.0)))
(klay "D-TEXT")
(entmake (list '(0 . "TEXT") (cons 8 "D-TEXT") (cons 10 '(5031.000000 29.480000 0.000000)) (cons 40 0.21) (cons 1 "Stone faces bonded to coordinated backing.") '(7 . "KITCHEN") '(50 . 0.0)))
(klay "D-TEXT")
(entmake (list '(0 . "TEXT") (cons 8 "D-TEXT") (cons 10 '(5031.000000 29.100000 0.000000)) (cons 40 0.21) (cons 1 "") '(7 . "KITCHEN") '(50 . 0.0)))
(klay "D-TEXT")
(entmake (list '(0 . "TEXT") (cons 8 "D-TEXT") (cons 10 '(5031.000000 28.720000 0.000000)) (cons 40 0.21) (cons 1 "CUTTING HOLDS") '(7 . "KITCHEN") '(50 . 0.0)))
(klay "D-TEXT")
(entmake (list '(0 . "TEXT") (cons 8 "D-TEXT") (cons 10 '(5031.000000 28.340000 0.000000)) (cons 40 0.21) (cons 1 "Field-template every visible end.") '(7 . "KITCHEN") '(50 . 0.0)))
(klay "D-TEXT")
(entmake (list '(0 . "TEXT") (cons 8 "D-TEXT") (cons 10 '(5031.000000 27.960000 0.000000)) (cons 40 0.21) (cons 1 "Confirm slab scan and vein registration.") '(7 . "KITCHEN") '(50 . 0.0)))
(klay "D-TEXT")
(entmake (list '(0 . "TEXT") (cons 8 "D-TEXT") (cons 10 '(5031.000000 27.580000 0.000000)) (cons 40 0.21) (cons 1 "C03 / B06 = 121.5 nominal.") '(7 . "KITCHEN") '(50 . 0.0)))
(klay "D-TEXT")
(entmake (list '(0 . "TEXT") (cons 8 "D-TEXT") (cons 10 '(5031.000000 27.200000 0.000000)) (cons 40 0.21) (cons 1 "123 slab leaves 1.5 gross only.") '(7 . "KITCHEN") '(50 . 0.0)))
(klay "D-TEXT")
(entmake (list '(0 . "TEXT") (cons 8 "D-TEXT") (cons 10 '(5031.000000 26.820000 0.000000)) (cons 40 0.21) (cons 1 "Kerf and trimming must be resolved.") '(7 . "KITCHEN") '(50 . 0.0)))
(klay "D-TEXT")
(entmake (list '(0 . "TEXT") (cons 8 "D-TEXT") (cons 10 '(5031.000000 26.440000 0.000000)) (cons 40 0.21) (cons 1 "Do not infer extra slab allowance.") '(7 . "KITCHEN") '(50 . 0.0)))
(klay "D-TEXT")
(entmake (list '(0 . "TEXT") (cons 8 "D-TEXT") (cons 10 '(5031.000000 26.060000 0.000000)) (cons 40 0.21) (cons 1 "") '(7 . "KITCHEN") '(50 . 0.0)))
(klay "D-TEXT")
(entmake (list '(0 . "TEXT") (cons 8 "D-TEXT") (cons 10 '(5031.000000 25.680000 0.000000)) (cons 40 0.21) (cons 1 "SEAMS") '(7 . "KITCHEN") '(50 . 0.0)))
(klay "D-TEXT")
(entmake (list '(0 . "TEXT") (cons 8 "D-TEXT") (cons 10 '(5031.000000 25.300000 0.000000)) (cons 40 0.21) (cons 1 "J-C counter and J-B backsplash at 42.") '(7 . "KITCHEN") '(50 . 0.0)))
(klay "D-TEXT")
(entmake (list '(0 . "TEXT") (cons 8 "D-TEXT") (cons 10 '(5031.000000 24.920000 0.000000)) (cons 40 0.21) (cons 1 "Align vertically below window.") '(7 . "KITCHEN") '(50 . 0.0)))
(klay "D-TEXT")
(entmake (list '(0 . "TEXT") (cons 8 "D-TEXT") (cons 10 '(5031.000000 24.540000 0.000000)) (cons 40 0.21) (cons 1 "Check sink-flange clearance to seam.") '(7 . "KITCHEN") '(50 . 0.0)))
(klay "D-TEXT")
(entmake (list '(0 . "TEXT") (cons 8 "D-TEXT") (cons 10 '(5031.000000 24.160000 0.000000)) (cons 40 0.21) (cons 1 "J-90: proposed mitred wall corners.") '(7 . "KITCHEN") '(50 . 0.0)))
(klay "D-TEXT")
(entmake (list '(0 . "TEXT") (cons 8 "D-TEXT") (cons 10 '(5031.000000 23.780000 0.000000)) (cons 40 0.21) (cons 1 "") '(7 . "KITCHEN") '(50 . 0.0)))
(klay "D-TEXT")
(entmake (list '(0 . "TEXT") (cons 8 "D-TEXT") (cons 10 '(5031.000000 23.400000 0.000000)) (cons 40 0.21) (cons 1 "SOURCE") '(7 . "KITCHEN") '(50 . 0.0)))
(klay "D-TEXT")
(entmake (list '(0 . "TEXT") (cons 8 "D-TEXT") (cons 10 '(5031.000000 23.020000 0.000000)) (cons 40 0.21) (cons 1 "R9 S04 / S07 / S08 / S09.") '(7 . "KITCHEN") '(50 . 0.0)))
(klay "D-TEXT")
(entmake (list '(0 . "TEXT") (cons 8 "D-TEXT") (cons 10 '(5031.000000 22.640000 0.000000)) (cons 40 0.21) (cons 1 "Details show intent, not fabrication.") '(7 . "KITCHEN") '(50 . 0.0)))
(setvar "DIMTXT" 0.84) (setvar "DIMASZ" 0.6) (setvar "DIMGAP" 0.32) (setvar "DIMEXO" 0.48) (setvar "DIMEXE" 0.48)
(if (tblsearch "DIMSTYLE" "KITCHEN_1_8") (command "_.-DIMSTYLE" "_S" "KITCHEN_1_8" "_Y") (command "_.-DIMSTYLE" "_S" "KITCHEN_1_8"))
(command "_.-DIMSTYLE" "_R" "KITCHEN_1_8")
(klay "D-TITLE")
(command "_.RECTANG" '(6003.200000 3.200000 0.000000) '(6188.800000 140.800000 0.000000))
(klay "D-TITLE")
(entmake (list '(0 . "LINE") (cons 8 "D-TITLE") (cons 10 '(6003.200000 13.600000 0.000000)) (cons 11 '(6188.800000 13.600000 0.000000))))
(klay "D-TITLE")
(entmake (list '(0 . "TEXT") (cons 8 "D-TITLE") (cons 10 '(6005.600000 6.400000 0.000000)) (cons 40 1.28) (cons 1 "KITCHEN RENOVATION") '(7 . "KITCHEN") '(50 . 0.0)))
(klay "D-TEXT")
(entmake (list '(0 . "TEXT") (cons 8 "D-TEXT") (cons 10 '(6005.600000 4.400000 0.000000)) (cons 40 0.72) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(6122.400000 8.960000 0.000000)) (cons 40 1.12) (cons 1 "Window stone coordination") '(7 . "KITCHEN") '(50 . 0.0)))
(klay "D-TEXT")
(entmake (list '(0 . "TEXT") (cons 8 "D-TEXT") (cons 10 '(6122.400000 5.600000 0.000000)) (cons 40 0.76) (cons 1 "22 OCT 2026  |  1-1/2 in. = 1 ft  |  24 x 18 in.  |  INCHES") '(7 . "KITCHEN") '(50 . 0.0)))
(klay "D-TITLE")
(entmake (list '(0 . "TEXT") (cons 8 "D-TITLE") (cons 10 '(6172.800000 6.000000 0.000000)) (cons 40 2.72) (cons 1 "A502") '(7 . "KITCHEN") '(50 . 0.0)))
(klay "D-TITLE")
(entmake (list '(0 . "TEXT") (cons 8 "D-TITLE") (cons 10 '(6005.600000 137.200000 0.000000)) (cons 40 1.84) (cons 1 "WINDOW STONE COORDINATION") '(7 . "KITCHEN") '(50 . 0.0)))
(klay "D-TEXT")
(entmake (list '(0 . "TEXT") (cons 8 "D-TEXT") (cons 10 '(6005.600000 134.880000 0.000000)) (cons 40 0.72) (cons 1 "SOURCE COORDINATION / 22 OCT 2026") '(7 . "KITCHEN") '(50 . 0.0)))
(klay "D-OUTLINE")
(command "_.RECTANG" '(6018.000000 49.000000 0.000000) '(6072.000000 113.000000 0.000000))
(klay "D-OUTLINE")
(command "_.RECTANG" '(6019.000000 49.000000 0.000000) '(6071.000000 97.000000 0.000000))
(klay "D-FINE")
(command "_.RECTANG" '(6020.500000 50.500000 0.000000) '(6069.500000 95.500000 0.000000))
(klay "D-OUTLINE")
(command "_.RECTANG" '(6018.000000 97.000000 0.000000) '(6072.000000 113.000000 0.000000))
(klay "D-FINE")
(command "_.RECTANG" '(6019.000000 49.000000 0.000000) '(6071.000000 49.472441 0.000000))
(klay "D-FINE")
(command "_.RECTANG" '(6019.000000 96.527559 0.000000) '(6071.000000 97.000000 0.000000))
(klay "D-FINE")
(command "_.RECTANG" '(6019.000000 49.472441 0.000000) '(6019.472441 96.527559 0.000000))
(klay "D-FINE")
(command "_.RECTANG" '(6070.527559 49.472441 0.000000) '(6071.000000 96.527559 0.000000))
(klay "D-FINE")
(entmake (list '(0 . "LINE") (cons 8 "D-FINE") (cons 10 '(6018.500000 74.000000 0.000000)) (cons 11 '(6010.000000 76.000000 0.000000))))
(klay "D-FINE")
(entmake (list '(0 . "LINE") (cons 8 "D-FINE") (cons 10 '(6010.000000 76.000000 0.000000)) (cons 11 '(6014.000000 76.000000 0.000000))))
(klay "D-TEXT")
(entmake (list '(0 . "TEXT") (cons 8 "D-TEXT") (cons 10 '(6014.600000 75.766667 0.000000)) (cons 40 0.84) (cons 1 "W01") '(7 . "KITCHEN") '(50 . 0.0)))
(klay "D-FINE")
(entmake (list '(0 . "LINE") (cons 8 "D-FINE") (cons 10 '(6071.500000 74.000000 0.000000)) (cons 11 '(6077.000000 76.000000 0.000000))))
(klay "D-FINE")
(entmake (list '(0 . "LINE") (cons 8 "D-FINE") (cons 10 '(6077.000000 76.000000 0.000000)) (cons 11 '(6081.000000 76.000000 0.000000))))
(klay "D-TEXT")
(entmake (list '(0 . "TEXT") (cons 8 "D-TEXT") (cons 10 '(6081.600000 75.766667 0.000000)) (cons 40 0.84) (cons 1 "W02") '(7 . "KITCHEN") '(50 . 0.0)))
(klay "D-TEXT")
(entmake (list '(0 . "TEXT") (cons 8 "D-TEXT") (cons 10 '(6042.000000 104.000000 0.000000)) (cons 40 1.2) (cons 1 "W03") '(7 . "KITCHEN") '(50 . 0.0)))
(klay "D-TEXT")
(entmake (list '(0 . "TEXT") (cons 8 "D-TEXT") (cons 10 '(6042.000000 51.000000 0.000000)) (cons 40 1) (cons 1 "W04") '(7 . "KITCHEN") '(50 . 0.0)))
(klay "D-TEXT")
(entmake (list '(0 . "TEXT") (cons 8 "D-TEXT") (cons 10 '(6042.000000 94.000000 0.000000)) (cons 40 1) (cons 1 "W05") '(7 . "KITCHEN") '(50 . 0.0)))
(klay "D-FINE")
(entmake (list '(0 . "LINE") (cons 8 "D-FINE") (cons 10 '(6019.200000 61.000000 0.000000)) (cons 11 '(6010.000000 65.000000 0.000000))))
(klay "D-FINE")
(entmake (list '(0 . "LINE") (cons 8 "D-FINE") (cons 10 '(6010.000000 65.000000 0.000000)) (cons 11 '(6014.000000 65.000000 0.000000))))
(klay "D-TEXT")
(entmake (list '(0 . "TEXT") (cons 8 "D-TEXT") (cons 10 '(6014.600000 64.766667 0.000000)) (cons 40 0.84) (cons 1 "W06") '(7 . "KITCHEN") '(50 . 0.0)))
(klay "D-FINE")
(entmake (list '(0 . "LINE") (cons 8 "D-FINE") (cons 10 '(6070.700000 61.000000 0.000000)) (cons 11 '(6077.000000 65.000000 0.000000))))
(klay "D-FINE")
(entmake (list '(0 . "LINE") (cons 8 "D-FINE") (cons 10 '(6077.000000 65.000000 0.000000)) (cons 11 '(6081.000000 65.000000 0.000000))))
(klay "D-TEXT")
(entmake (list '(0 . "TEXT") (cons 8 "D-TEXT") (cons 10 '(6081.600000 64.766667 0.000000)) (cons 40 0.84) (cons 1 "W07") '(7 . "KITCHEN") '(50 . 0.0)))
(klay "D-DIMS")
(command "_.DIMLINEAR" '(6019.000000 97.000000 0.000000) '(6071.000000 97.000000 0.000000) "_H" '(6045.000000 120.000000 0.000000))
(klay "D-TITLE")
(entmake (list '(0 . "TEXT") (cons 8 "D-TITLE") (cons 10 '(6018.000000 32.000000 0.000000)) (cons 40 1.4) (cons 1 "12  INTERIOR ELEVATION") '(7 . "KITCHEN") '(50 . 0.0)))
(klay "D-TEXT")
(entmake (list '(0 . "TEXT") (cons 8 "D-TEXT") (cons 10 '(6018.000000 29.000000 0.000000)) (cons 40 0.9) (cons 1 "52 nominal window / 49 study glass / height and reveals by field template") '(7 . "KITCHEN") '(50 . 0.0)))
(klay "D-TEXT")
(entmake (list '(0 . "TEXT") (cons 8 "D-TEXT") (cons 10 '(6103.000000 123.000000 0.000000)) (cons 40 0.84) (cons 1 "SEVEN PIECES / ONE COORDINATED OPENING") '(7 . "KITCHEN") '(50 . 0.0)))
(klay "D-TEXT")
(entmake (list '(0 . "TEXT") (cons 8 "D-TEXT") (cons 10 '(6103.000000 121.480000 0.000000)) (cons 40 0.84) (cons 1 "W01  Wall face left of opening") '(7 . "KITCHEN") '(50 . 0.0)))
(klay "D-TEXT")
(entmake (list '(0 . "TEXT") (cons 8 "D-TEXT") (cons 10 '(6103.000000 119.960000 0.000000)) (cons 40 0.84) (cons 1 "W02  Wall face right of opening") '(7 . "KITCHEN") '(50 . 0.0)))
(klay "D-TEXT")
(entmake (list '(0 . "TEXT") (cons 8 "D-TEXT") (cons 10 '(6103.000000 118.440000 0.000000)) (cons 40 0.84) (cons 1 "W03  Wall face above opening") '(7 . "KITCHEN") '(50 . 0.0)))
(klay "D-TEXT")
(entmake (list '(0 . "TEXT") (cons 8 "D-TEXT") (cons 10 '(6103.000000 116.920000 0.000000)) (cons 40 0.84) (cons 1 "W04  Sill / bottom reveal") '(7 . "KITCHEN") '(50 . 0.0)))
(klay "D-TEXT")
(entmake (list '(0 . "TEXT") (cons 8 "D-TEXT") (cons 10 '(6103.000000 115.400000 0.000000)) (cons 40 0.84) (cons 1 "W05  Head / top reveal") '(7 . "KITCHEN") '(50 . 0.0)))
(klay "D-TEXT")
(entmake (list '(0 . "TEXT") (cons 8 "D-TEXT") (cons 10 '(6103.000000 113.880000 0.000000)) (cons 40 0.84) (cons 1 "W06  Left internal jamb") '(7 . "KITCHEN") '(50 . 0.0)))
(klay "D-TEXT")
(entmake (list '(0 . "TEXT") (cons 8 "D-TEXT") (cons 10 '(6103.000000 112.360000 0.000000)) (cons 40 0.84) (cons 1 "W07  Right internal jamb") '(7 . "KITCHEN") '(50 . 0.0)))
(klay "D-TEXT")
(entmake (list '(0 . "TEXT") (cons 8 "D-TEXT") (cons 10 '(6103.000000 110.840000 0.000000)) (cons 40 0.84) (cons 1 "") '(7 . "KITCHEN") '(50 . 0.0)))
(klay "D-TEXT")
(entmake (list '(0 . "TEXT") (cons 8 "D-TEXT") (cons 10 '(6103.000000 109.320000 0.000000)) (cons 40 0.84) (cons 1 "FIELD TEMPLATE REQUIRED") '(7 . "KITCHEN") '(50 . 0.0)))
(klay "D-TEXT")
(entmake (list '(0 . "TEXT") (cons 8 "D-TEXT") (cons 10 '(6103.000000 107.800000 0.000000)) (cons 40 0.84) (cons 1 "52 nominal width / 59.25 shared centreline.") '(7 . "KITCHEN") '(50 . 0.0)))
(klay "D-TEXT")
(entmake (list '(0 . "TEXT") (cons 8 "D-TEXT") (cons 10 '(6103.000000 106.280000 0.000000)) (cons 40 0.84) (cons 1 "Drawing flags 1/4 in. centreline discrepancy.") '(7 . "KITCHEN") '(50 . 0.0)))
(klay "D-TEXT")
(entmake (list '(0 . "TEXT") (cons 8 "D-TEXT") (cons 10 '(6103.000000 104.760000 0.000000)) (cons 40 0.84) (cons 1 "Study sill 44, head 92; not surveyed levels.") '(7 . "KITCHEN") '(50 . 0.0)))
(klay "D-TEXT")
(entmake (list '(0 . "TEXT") (cons 8 "D-TEXT") (cons 10 '(6103.000000 103.240000 0.000000)) (cons 40 0.84) (cons 1 "Opening height and depth require measurement.") '(7 . "KITCHEN") '(50 . 0.0)))
(klay "D-TEXT")
(entmake (list '(0 . "TEXT") (cons 8 "D-TEXT") (cons 10 '(6103.000000 101.720000 0.000000)) (cons 40 0.84) (cons 1 "Frame, sash and drainage must remain operable.") '(7 . "KITCHEN") '(50 . 0.0)))
(klay "D-TEXT")
(entmake (list '(0 . "TEXT") (cons 8 "D-TEXT") (cons 10 '(6103.000000 100.200000 0.000000)) (cons 40 0.84) (cons 1 "Blinds and internal applied trim removed.") '(7 . "KITCHEN") '(50 . 0.0)))
(klay "D-TEXT")
(entmake (list '(0 . "TEXT") (cons 8 "D-TEXT") (cons 10 '(6103.000000 98.680000 0.000000)) (cons 40 0.84) (cons 1 "") '(7 . "KITCHEN") '(50 . 0.0)))
(klay "D-TEXT")
(entmake (list '(0 . "TEXT") (cons 8 "D-TEXT") (cons 10 '(6103.000000 97.160000 0.000000)) (cons 40 0.84) (cons 1 "MATERIAL") '(7 . "KITCHEN") '(50 . 0.0)))
(klay "D-TEXT")
(entmake (list '(0 . "TEXT") (cons 8 "D-TEXT") (cons 10 '(6103.000000 95.640000 0.000000)) (cons 40 0.84) (cons 1 "All seven pieces 12 mm Statuario porcelain.") '(7 . "KITCHEN") '(50 . 0.0)))
(klay "D-TEXT")
(entmake (list '(0 . "TEXT") (cons 8 "D-TEXT") (cons 10 '(6103.000000 94.120000 0.000000)) (cons 40 0.84) (cons 1 "Shop-coordinate mitres, face/reveal joints,") '(7 . "KITCHEN") '(50 . 0.0)))
(klay "D-TEXT")
(entmake (list '(0 . "TEXT") (cons 8 "D-TEXT") (cons 10 '(6103.000000 92.600000 0.000000)) (cons 40 0.84) (cons 1 "finish and matched vein direction.") '(7 . "KITCHEN") '(50 . 0.0)))
(klay "D-TEXT")
(entmake (list '(0 . "TEXT") (cons 8 "D-TEXT") (cons 10 '(6103.000000 91.080000 0.000000)) (cons 40 0.84) (cons 1 "Do not derive cut sizes from this study.") '(7 . "KITCHEN") '(50 . 0.0)))
(klay "D-TEXT")
(entmake (list '(0 . "TEXT") (cons 8 "D-TEXT") (cons 10 '(6103.000000 89.560000 0.000000)) (cons 40 0.84) (cons 1 "") '(7 . "KITCHEN") '(50 . 0.0)))
(klay "D-TEXT")
(entmake (list '(0 . "TEXT") (cons 8 "D-TEXT") (cons 10 '(6103.000000 88.040000 0.000000)) (cons 40 0.84) (cons 1 "SOURCE") '(7 . "KITCHEN") '(50 . 0.0)))
(klay "D-TEXT")
(entmake (list '(0 . "TEXT") (cons 8 "D-TEXT") (cons 10 '(6103.000000 86.520000 0.000000)) (cons 40 0.84) (cons 1 "Owner coordination notes; Cabinet p. 6; R9 S03 / S10.") '(7 . "KITCHEN") '(50 . 0.0)))
(setvar "DIMTXT" 1.26) (setvar "DIMASZ" 0.8999999999999999) (setvar "DIMGAP" 0.48) (setvar "DIMEXO" 0.72) (setvar "DIMEXE" 0.72)
(if (tblsearch "DIMSTYLE" "KITCHEN_1_12") (command "_.-DIMSTYLE" "_S" "KITCHEN_1_12" "_Y") (command "_.-DIMSTYLE" "_S" "KITCHEN_1_12"))
(command "_.-DIMSTYLE" "_R" "KITCHEN_1_12")
(klay "D-TITLE")
(command "_.RECTANG" '(7004.800000 4.800000 0.000000) '(7283.200000 211.200000 0.000000))
(klay "D-TITLE")
(entmake (list '(0 . "LINE") (cons 8 "D-TITLE") (cons 10 '(7004.800000 20.400000 0.000000)) (cons 11 '(7283.200000 20.400000 0.000000))))
(klay "D-TITLE")
(entmake (list '(0 . "TEXT") (cons 8 "D-TITLE") (cons 10 '(7008.400000 9.600000 0.000000)) (cons 40 1.92) (cons 1 "KITCHEN RENOVATION") '(7 . "KITCHEN") '(50 . 0.0)))
(klay "D-TEXT")
(entmake (list '(0 . "TEXT") (cons 8 "D-TEXT") (cons 10 '(7008.400000 6.600000 0.000000)) (cons 40 1.08) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(7183.600000 13.440000 0.000000)) (cons 40 1.6800000000000002) (cons 1 "Selected hood and range stone") '(7 . "KITCHEN") '(50 . 0.0)))
(klay "D-TEXT")
(entmake (list '(0 . "TEXT") (cons 8 "D-TEXT") (cons 10 '(7183.600000 8.400000 0.000000)) (cons 40 1.1400000000000001) (cons 1 "22 OCT 2026  |  1 in. = 1 ft  |  24 x 18 in.  |  INCHES") '(7 . "KITCHEN") '(50 . 0.0)))
(klay "D-TITLE")
(entmake (list '(0 . "TEXT") (cons 8 "D-TITLE") (cons 10 '(7259.200000 9.000000 0.000000)) (cons 40 4.08) (cons 1 "A602") '(7 . "KITCHEN") '(50 . 0.0)))
(klay "D-TITLE")
(entmake (list '(0 . "TEXT") (cons 8 "D-TITLE") (cons 10 '(7008.400000 205.800000 0.000000)) (cons 40 2.7600000000000002) (cons 1 "SELECTED HOOD AND RANGE STONE") '(7 . "KITCHEN") '(50 . 0.0)))
(klay "D-TEXT")
(entmake (list '(0 . "TEXT") (cons 8 "D-TEXT") (cons 10 '(7008.400000 202.320000 0.000000)) (cons 40 1.08) (cons 1 "SOURCE COORDINATION / 22 OCT 2026") '(7 . "KITCHEN") '(50 . 0.0)))
(klay "D-OUTLINE")
(command "_.RECTANG" '(7025.000000 66.000000 0.000000) '(7091.000000 174.000000 0.000000))
(klay "D-OUTLINE")
(entmake (list '(0 . "LINE") (cons 8 "D-OUTLINE") (cons 10 '(7025.000000 102.000000 0.000000)) (cons 11 '(7091.000000 102.000000 0.000000))))
(klay "D-OUTLINE")
(command "_.RECTANG" '(7025.000000 122.000000 0.000000) '(7042.000000 174.000000 0.000000))
(klay "D-OUTLINE")
(command "_.RECTANG" '(7042.000000 134.245350 0.000000) '(7058.000000 174.000000 0.000000))
(klay "D-OUTLINE")
(command "_.RECTANG" '(7058.000000 134.245350 0.000000) '(7074.000000 174.000000 0.000000))
(klay "D-OUTLINE")
(command "_.RECTANG" '(7074.000000 122.000000 0.000000) '(7091.000000 174.000000 0.000000))
(klay "D-OUTLINE")
(command "_.RECTANG" '(7043.000000 132.080000 0.000000) '(7073.000000 134.245350 0.000000))
(klay "D-OUTLINE")
(entmake (list '(0 . "LINE") (cons 8 "D-OUTLINE") (cons 10 '(7043.000000 132.000000 0.000000)) (cons 11 '(7073.000000 132.000000 0.000000))))
(klay "D-OUTLINE")
(command "_.RECTANG" '(7042.750000 67.500000 0.000000) '(7072.500000 102.000000 0.000000))
(klay "D-OUTLINE")
(command "_.RECTANG" '(7044.550000 72.600000 0.000000) '(7070.450000 92.400000 0.000000))
(klay "D-DIMS")
(command "_.DIMLINEAR" '(7074.000000 134.245350 0.000000) '(7074.000000 174.000000 0.000000) "_V" '(7085.000000 154.122675 0.000000))
(klay "D-DIMS")
(command "_.DIMLINEAR" '(7058.000000 102.000000 0.000000) '(7058.000000 132.000000 0.000000) "_V" '(7058.000000 117.000000 0.000000))
(klay "D-TITLE")
(entmake (list '(0 . "TEXT") (cons 8 "D-TITLE") (cons 10 '(7025.000000 48.000000 0.000000)) (cons 40 1.5) (cons 1 "14  SELECTED B / 30 IN. LOWEST CLEARANCE") '(7 . "KITCHEN") '(50 . 0.0)))
(klay "D-TEXT")
(entmake (list '(0 . "TEXT") (cons 8 "D-TEXT") (cons 10 '(7025.000000 41.000000 0.000000)) (cons 40 1.26) (cons 1 "Owner selection 22 Oct; actual Sakura dimensions pending.") '(7 . "KITCHEN") '(50 . 0.0)))
(klay "D-TEXT")
(entmake (list '(0 . "TEXT") (cons 8 "D-TEXT") (cons 10 '(7025.000000 38.720000 0.000000)) (cons 40 1.26) (cons 1 "Stone bottom approx. 68-1/4; centre height approx. 39-3/4.") '(7 . "KITCHEN") '(50 . 0.0)))
(klay "D-OUTLINE")
(entmake (list '(0 . "LINE") (cons 8 "D-OUTLINE") (cons 10 '(7133.000000 97.000000 0.000000)) (cons 11 '(7163.500000 97.000000 0.000000))))
(klay "D-OUTLINE")
(entmake (list '(0 . "LINE") (cons 8 "D-OUTLINE") (cons 10 '(7163.500000 97.000000 0.000000)) (cons 11 '(7163.500000 122.000000 0.000000))))
(klay "D-OUTLINE")
(entmake (list '(0 . "LINE") (cons 8 "D-OUTLINE") (cons 10 '(7163.500000 122.000000 0.000000)) (cons 11 '(7164.250000 122.000000 0.000000))))
(klay "D-OUTLINE")
(entmake (list '(0 . "LINE") (cons 8 "D-OUTLINE") (cons 10 '(7164.250000 122.000000 0.000000)) (cons 11 '(7164.250000 134.245350 0.000000))))
(klay "D-OUTLINE")
(entmake (list '(0 . "LINE") (cons 8 "D-OUTLINE") (cons 10 '(7164.250000 134.245350 0.000000)) (cons 11 '(7132.250000 134.245350 0.000000))))
(klay "D-OUTLINE")
(entmake (list '(0 . "LINE") (cons 8 "D-OUTLINE") (cons 10 '(7132.250000 134.245350 0.000000)) (cons 11 '(7132.250000 122.000000 0.000000))))
(klay "D-OUTLINE")
(entmake (list '(0 . "LINE") (cons 8 "D-OUTLINE") (cons 10 '(7132.250000 122.000000 0.000000)) (cons 11 '(7133.000000 122.000000 0.000000))))
(klay "D-OUTLINE")
(entmake (list '(0 . "LINE") (cons 8 "D-OUTLINE") (cons 10 '(7133.000000 122.000000 0.000000)) (cons 11 '(7133.000000 97.000000 0.000000))))
(klay "D-HIDDEN")
(entmake (list '(0 . "LINE") (cons 8 "D-HIDDEN") (cons 10 '(7124.000000 102.000000 0.000000)) (cons 11 '(7173.000000 102.000000 0.000000))))
(klay "D-TEXT")
(entmake (list '(0 . "TEXT") (cons 8 "D-TEXT") (cons 10 '(7167.000000 103.000000 0.000000)) (cons 40 1.05) (cons 1 "COUNTER 36") '(7 . "KITCHEN") '(50 . 0.0)))
(klay "D-TITLE")
(entmake (list '(0 . "TEXT") (cons 8 "D-TITLE") (cons 10 '(7141.000000 113.000000 0.000000)) (cons 40 2) (cons 1 "B03") '(7 . "KITCHEN") '(50 . 0.0)))
(klay "D-DIMS")
(command "_.DIMLINEAR" '(7133.000000 97.000000 0.000000) '(7163.500000 97.000000 0.000000) "_H" '(7148.250000 90.000000 0.000000))
(klay "D-DIMS")
(command "_.DIMLINEAR" '(7132.250000 134.245350 0.000000) '(7164.250000 134.245350 0.000000) "_H" '(7148.250000 141.245350 0.000000))
(klay "D-DIMS")
(command "_.DIMLINEAR" '(7133.000000 97.000000 0.000000) '(7133.000000 102.000000 0.000000) "_V" '(7127.000000 99.500000 0.000000))
(klay "D-DIMS")
(command "_.DIMLINEAR" '(7164.250000 97.000000 0.000000) '(7164.250000 134.245350 0.000000) "_V" '(7174.000000 115.622675 0.000000))
(klay "D-DIMS")
(command "_.DIMLINEAR" '(7133.000000 102.000000 0.000000) '(7133.000000 122.000000 0.000000) "_V" '(7120.000000 112.000000 0.000000))
(klay "D-TITLE")
(entmake (list '(0 . "TEXT") (cons 8 "D-TITLE") (cons 10 '(7122.000000 48.000000 0.000000)) (cons 40 1.5) (cons 1 "15  B03 / RANGE OMITTED") '(7 . "KITCHEN") '(50 . 0.0)))
(klay "D-TEXT")
(entmake (list '(0 . "TEXT") (cons 8 "D-TEXT") (cons 10 '(7122.000000 41.000000 0.000000)) (cons 40 1.26) (cons 1 "12 mm Statuario porcelain; stepped single piece.") '(7 . "KITCHEN") '(50 . 0.0)))
(klay "D-TEXT")
(entmake (list '(0 . "TEXT") (cons 8 "D-TEXT") (cons 10 '(7122.000000 38.720000 0.000000)) (cons 40 1.26) (cons 1 "5 below counter is from R9 S05 / S08.") '(7 . "KITCHEN") '(50 . 0.0)))
(klay "D-TEXT")
(entmake (list '(0 . "TEXT") (cons 8 "D-TEXT") (cons 10 '(7211.000000 183.000000 0.000000)) (cons 40 1.26) (cons 1 "SELECTED DESIGN") '(7 . "KITCHEN") '(50 . 0.0)))
(klay "D-TEXT")
(entmake (list '(0 . "TEXT") (cons 8 "D-TEXT") (cons 10 '(7211.000000 180.720000 0.000000)) (cons 40 1.26) (cons 1 "B selected by owner 22 October.") '(7 . "KITCHEN") '(50 . 0.0)))
(klay "D-TEXT")
(entmake (list '(0 . "TEXT") (cons 8 "D-TEXT") (cons 10 '(7211.000000 178.440000 0.000000)) (cons 40 1.26) (cons 1 "A is superseded in this issue.") '(7 . "KITCHEN") '(50 . 0.0)))
(klay "D-TEXT")
(entmake (list '(0 . "TEXT") (cons 8 "D-TEXT") (cons 10 '(7211.000000 176.160000 0.000000)) (cons 40 1.26) (cons 1 "Lowest modeled underside = 66.") '(7 . "KITCHEN") '(50 . 0.0)))
(klay "D-TEXT")
(entmake (list '(0 . "TEXT") (cons 8 "D-TEXT") (cons 10 '(7211.000000 173.880000 0.000000)) (cons 40 1.26) (cons 1 "Electric cooktop = 36; clearance = 30.") '(7 . "KITCHEN") '(50 . 0.0)))
(klay "D-TEXT")
(entmake (list '(0 . "TEXT") (cons 8 "D-TEXT") (cons 10 '(7211.000000 171.600000 0.000000)) (cons 40 1.26) (cons 1 "") '(7 . "KITCHEN") '(50 . 0.0)))
(klay "D-TEXT")
(entmake (list '(0 . "TEXT") (cons 8 "D-TEXT") (cons 10 '(7211.000000 169.320000 0.000000)) (cons 40 1.26) (cons 1 "B03 IS NOT THE HOOD FRONT") '(7 . "KITCHEN") '(50 . 0.0)))
(klay "D-TEXT")
(entmake (list '(0 . "TEXT") (cons 8 "D-TEXT") (cons 10 '(7211.000000 167.040000 0.000000)) (cons 40 1.26) (cons 1 "R9: 30.5 lower / 32 upper width.") '(7 . "KITCHEN") '(50 . 0.0)))
(klay "D-TEXT")
(entmake (list '(0 . "TEXT") (cons 8 "D-TEXT") (cons 10 '(7211.000000 164.760000 0.000000)) (cons 40 1.26) (cons 1 "5 below counter: bottom 31.") '(7 . "KITCHEN") '(50 . 0.0)))
(klay "D-TEXT")
(entmake (list '(0 . "TEXT") (cons 8 "D-TEXT") (cons 10 '(7211.000000 162.480000 0.000000)) (cons 40 1.26) (cons 1 "Shoulder step at 56.") '(7 . "KITCHEN") '(50 . 0.0)))
(klay "D-TEXT")
(entmake (list '(0 . "TEXT") (cons 8 "D-TEXT") (cons 10 '(7211.000000 160.200000 0.000000)) (cons 40 1.26) (cons 1 "Top aligned to selected B stone datum.") '(7 . "KITCHEN") '(50 . 0.0)))
(klay "D-TEXT")
(entmake (list '(0 . "TEXT") (cons 8 "D-TEXT") (cons 10 '(7211.000000 157.920000 0.000000)) (cons 40 1.26) (cons 1 "Overall approx. 37-1/4 is derived;") '(7 . "KITCHEN") '(50 . 0.0)))
(klay "D-TEXT")
(entmake (list '(0 . "TEXT") (cons 8 "D-TEXT") (cons 10 '(7211.000000 155.640000 0.000000)) (cons 40 1.26) (cons 1 "not a field measurement or cut size.") '(7 . "KITCHEN") '(50 . 0.0)))
(klay "D-TEXT")
(entmake (list '(0 . "TEXT") (cons 8 "D-TEXT") (cons 10 '(7211.000000 153.360000 0.000000)) (cons 40 1.26) (cons 1 "Final top/template against actual Sakura.") '(7 . "KITCHEN") '(50 . 0.0)))
(klay "D-TEXT")
(entmake (list '(0 . "TEXT") (cons 8 "D-TEXT") (cons 10 '(7211.000000 151.080000 0.000000)) (cons 40 1.26) (cons 1 "") '(7 . "KITCHEN") '(50 . 0.0)))
(klay "D-TEXT")
(entmake (list '(0 . "TEXT") (cons 8 "D-TEXT") (cons 10 '(7211.000000 148.800000 0.000000)) (cons 40 1.26) (cons 1 "HOOD / FABRICATION HOLDS") '(7 . "KITCHEN") '(50 . 0.0)))
(klay "D-TEXT")
(entmake (list '(0 . "TEXT") (cons 8 "D-TEXT") (cons 10 '(7211.000000 146.520000 0.000000)) (cons 40 1.26) (cons 1 "Actual Sakura underside and casing.") '(7 . "KITCHEN") '(50 . 0.0)))
(klay "D-TEXT")
(entmake (list '(0 . "TEXT") (cons 8 "D-TEXT") (cons 10 '(7211.000000 144.240000 0.000000)) (cons 40 1.26) (cons 1 "Manufacturer installation requirements.") '(7 . "KITCHEN") '(50 . 0.0)))
(klay "D-TEXT")
(entmake (list '(0 . "TEXT") (cons 8 "D-TEXT") (cons 10 '(7211.000000 141.960000 0.000000)) (cons 40 1.26) (cons 1 "Stone/substrate/adhesive system.") '(7 . "KITCHEN") '(50 . 0.0)))
(klay "D-TEXT")
(entmake (list '(0 . "TEXT") (cons 8 "D-TEXT") (cons 10 '(7211.000000 139.680000 0.000000)) (cons 40 1.26) (cons 1 "Return depth; hinges and rated loads.") '(7 . "KITCHEN") '(50 . 0.0)))
(klay "D-TEXT")
(entmake (list '(0 . "TEXT") (cons 8 "D-TEXT") (cons 10 '(7211.000000 137.400000 0.000000)) (cons 40 1.26) (cons 1 "Flue route, size and support.") '(7 . "KITCHEN") '(50 . 0.0)))
(klay "D-TEXT")
(entmake (list '(0 . "TEXT") (cons 8 "D-TEXT") (cons 10 '(7211.000000 135.120000 0.000000)) (cons 40 1.26) (cons 1 "") '(7 . "KITCHEN") '(50 . 0.0)))
(klay "D-TEXT")
(entmake (list '(0 . "TEXT") (cons 8 "D-TEXT") (cons 10 '(7211.000000 132.840000 0.000000)) (cons 40 1.26) (cons 1 "SOURCE") '(7 . "KITCHEN") '(50 . 0.0)))
(klay "D-TEXT")
(entmake (list '(0 . "TEXT") (cons 8 "D-TEXT") (cons 10 '(7211.000000 130.560000 0.000000)) (cons 40 1.26) (cons 1 "Owner coordination notes 22 October.") '(7 . "KITCHEN") '(50 . 0.0)))
(klay "D-TEXT")
(entmake (list '(0 . "TEXT") (cons 8 "D-TEXT") (cons 10 '(7211.000000 128.280000 0.000000)) (cons 40 1.26) (cons 1 "Stone R9 S05 / S08; Cabinet p. 5.") '(7 . "KITCHEN") '(50 . 0.0)))
(klay "D-TEXT")
(entmake (list '(0 . "TEXT") (cons 8 "D-TEXT") (cons 10 '(7211.000000 126.000000 0.000000)) (cons 40 1.26) (cons 1 "Source 34 overall belongs to old level;") '(7 . "KITCHEN") '(50 . 0.0)))
(klay "D-TEXT")
(entmake (list '(0 . "TEXT") (cons 8 "D-TEXT") (cons 10 '(7211.000000 123.720000 0.000000)) (cons 40 1.26) (cons 1 "5 below-counter continuation retained.") '(7 . "KITCHEN") '(50 . 0.0)))
(setvar "DIMTXT" 1.26) (setvar "DIMASZ" 0.8999999999999999) (setvar "DIMGAP" 0.48) (setvar "DIMEXO" 0.72) (setvar "DIMEXE" 0.72)
(if (tblsearch "DIMSTYLE" "KITCHEN_1_12") (command "_.-DIMSTYLE" "_S" "KITCHEN_1_12" "_Y") (command "_.-DIMSTYLE" "_S" "KITCHEN_1_12"))
(command "_.-DIMSTYLE" "_R" "KITCHEN_1_12")
(klay "D-TITLE")
(command "_.RECTANG" '(8004.800000 4.800000 0.000000) '(8283.200000 211.200000 0.000000))
(klay "D-TITLE")
(entmake (list '(0 . "LINE") (cons 8 "D-TITLE") (cons 10 '(8004.800000 20.400000 0.000000)) (cons 11 '(8283.200000 20.400000 0.000000))))
(klay "D-TITLE")
(entmake (list '(0 . "TEXT") (cons 8 "D-TITLE") (cons 10 '(8008.400000 9.600000 0.000000)) (cons 40 1.92) (cons 1 "KITCHEN RENOVATION") '(7 . "KITCHEN") '(50 . 0.0)))
(klay "D-TEXT")
(entmake (list '(0 . "TEXT") (cons 8 "D-TEXT") (cons 10 '(8008.400000 6.600000 0.000000)) (cons 40 1.08) (cons 1 "DESIGN COORDINATION STUDY  -  FIELD VERIFY  -  NOT FOR CONSTRUCTION") '(7 . "KITCHEN") '(50 . 0.0)))
(klay "D-TITLE")
(entmake (list '(0 . "TEXT") (cons 8 "D-TITLE") (cons 10 '(8183.600000 13.440000 0.000000)) (cons 40 1.6800000000000002) (cons 1 "Pullouts and pocket door details") '(7 . "KITCHEN") '(50 . 0.0)))
(klay "D-TEXT")
(entmake (list '(0 . "TEXT") (cons 8 "D-TEXT") (cons 10 '(8183.600000 8.400000 0.000000)) (cons 40 1.1400000000000001) (cons 1 "22 OCT 2026  |  1 in. = 1 ft  |  24 x 18 in.  |  INCHES") '(7 . "KITCHEN") '(50 . 0.0)))
(klay "D-TITLE")
(entmake (list '(0 . "TEXT") (cons 8 "D-TITLE") (cons 10 '(8259.200000 9.000000 0.000000)) (cons 40 4.08) (cons 1 "A402") '(7 . "KITCHEN") '(50 . 0.0)))
(klay "D-TITLE")
(entmake (list '(0 . "TEXT") (cons 8 "D-TITLE") (cons 10 '(8008.400000 205.800000 0.000000)) (cons 40 2.7600000000000002) (cons 1 "PULLOUTS AND POCKET DOOR DETAILS") '(7 . "KITCHEN") '(50 . 0.0)))
(klay "D-TEXT")
(entmake (list '(0 . "TEXT") (cons 8 "D-TEXT") (cons 10 '(8008.400000 202.320000 0.000000)) (cons 40 1.08) (cons 1 "SOURCE COORDINATION / 22 OCT 2026") '(7 . "KITCHEN") '(50 . 0.0)))
(klay "D-OUTLINE")
(command "_.RECTANG" '(8025.000000 135.000000 0.000000) '(8035.000000 169.500000 0.000000))
(klay "D-OUTLINE")
(command "_.RECTANG" '(8025.000000 139.000000 0.000000) '(8035.000000 169.500000 0.000000))
(klay "D-OUTLINE")
(command "_.RECTANG" '(8027.323000 167.962200 0.000000) '(8032.677000 168.237800 0.000000))
(klay "D-DIMS")
(command "_.DIMLINEAR" '(8025.000000 169.500000 0.000000) '(8035.000000 169.500000 0.000000) "_H" '(8030.000000 177.000000 0.000000))
(klay "D-TITLE")
(entmake (list '(0 . "TEXT") (cons 8 "D-TITLE") (cons 10 '(8021.000000 127.000000 0.000000)) (cons 40 1.15) (cons 1 "SPICE / LEFT OF RANGE") '(7 . "KITCHEN") '(50 . 0.0)))
(klay "D-TEXT")
(entmake (list '(0 . "TEXT") (cons 8 "D-TEXT") (cons 10 '(8021.000000 123.000000 0.000000)) (cons 40 1.1) (cons 1 "FULL-HEIGHT PULLOUT") '(7 . "KITCHEN") '(50 . 0.0)))
(klay "D-OUTLINE")
(command "_.RECTANG" '(8045.000000 135.000000 0.000000) '(8069.250000 169.500000 0.000000))
(klay "D-OUTLINE")
(command "_.RECTANG" '(8068.500000 139.000000 0.000000) '(8069.250000 169.500000 0.000000))
(klay "D-HATCH")
(entmake (list '(0 . "LINE") (cons 8 "D-HATCH") (cons 10 '(8068.500000 140.000000 0.000000)) (cons 11 '(8069.250000 139.250000 0.000000))))
(klay "D-HATCH")
(entmake (list '(0 . "LINE") (cons 8 "D-HATCH") (cons 10 '(8068.500000 141.000000 0.000000)) (cons 11 '(8069.250000 140.250000 0.000000))))
(klay "D-HATCH")
(entmake (list '(0 . "LINE") (cons 8 "D-HATCH") (cons 10 '(8068.500000 142.000000 0.000000)) (cons 11 '(8069.250000 141.250000 0.000000))))
(klay "D-HATCH")
(entmake (list '(0 . "LINE") (cons 8 "D-HATCH") (cons 10 '(8068.500000 143.000000 0.000000)) (cons 11 '(8069.250000 142.250000 0.000000))))
(klay "D-HATCH")
(entmake (list '(0 . "LINE") (cons 8 "D-HATCH") (cons 10 '(8068.500000 144.000000 0.000000)) (cons 11 '(8069.250000 143.250000 0.000000))))
(klay "D-HATCH")
(entmake (list '(0 . "LINE") (cons 8 "D-HATCH") (cons 10 '(8068.500000 145.000000 0.000000)) (cons 11 '(8069.250000 144.250000 0.000000))))
(klay "D-HATCH")
(entmake (list '(0 . "LINE") (cons 8 "D-HATCH") (cons 10 '(8068.500000 146.000000 0.000000)) (cons 11 '(8069.250000 145.250000 0.000000))))
(klay "D-HATCH")
(entmake (list '(0 . "LINE") (cons 8 "D-HATCH") (cons 10 '(8068.500000 147.000000 0.000000)) (cons 11 '(8069.250000 146.250000 0.000000))))
(klay "D-HATCH")
(entmake (list '(0 . "LINE") (cons 8 "D-HATCH") (cons 10 '(8068.500000 148.000000 0.000000)) (cons 11 '(8069.250000 147.250000 0.000000))))
(klay "D-HATCH")
(entmake (list '(0 . "LINE") (cons 8 "D-HATCH") (cons 10 '(8068.500000 149.000000 0.000000)) (cons 11 '(8069.250000 148.250000 0.000000))))
(klay "D-HATCH")
(entmake (list '(0 . "LINE") (cons 8 "D-HATCH") (cons 10 '(8068.500000 150.000000 0.000000)) (cons 11 '(8069.250000 149.250000 0.000000))))
(klay "D-HATCH")
(entmake (list '(0 . "LINE") (cons 8 "D-HATCH") (cons 10 '(8068.500000 151.000000 0.000000)) (cons 11 '(8069.250000 150.250000 0.000000))))
(klay "D-HATCH")
(entmake (list '(0 . "LINE") (cons 8 "D-HATCH") (cons 10 '(8068.500000 152.000000 0.000000)) (cons 11 '(8069.250000 151.250000 0.000000))))
(klay "D-HATCH")
(entmake (list '(0 . "LINE") (cons 8 "D-HATCH") (cons 10 '(8068.500000 153.000000 0.000000)) (cons 11 '(8069.250000 152.250000 0.000000))))
(klay "D-HATCH")
(entmake (list '(0 . "LINE") (cons 8 "D-HATCH") (cons 10 '(8068.500000 154.000000 0.000000)) (cons 11 '(8069.250000 153.250000 0.000000))))
(klay "D-HATCH")
(entmake (list '(0 . "LINE") (cons 8 "D-HATCH") (cons 10 '(8068.500000 155.000000 0.000000)) (cons 11 '(8069.250000 154.250000 0.000000))))
(klay "D-HATCH")
(entmake (list '(0 . "LINE") (cons 8 "D-HATCH") (cons 10 '(8068.500000 156.000000 0.000000)) (cons 11 '(8069.250000 155.250000 0.000000))))
(klay "D-HATCH")
(entmake (list '(0 . "LINE") (cons 8 "D-HATCH") (cons 10 '(8068.500000 157.000000 0.000000)) (cons 11 '(8069.250000 156.250000 0.000000))))
(klay "D-HATCH")
(entmake (list '(0 . "LINE") (cons 8 "D-HATCH") (cons 10 '(8068.500000 158.000000 0.000000)) (cons 11 '(8069.250000 157.250000 0.000000))))
(klay "D-HATCH")
(entmake (list '(0 . "LINE") (cons 8 "D-HATCH") (cons 10 '(8068.500000 159.000000 0.000000)) (cons 11 '(8069.250000 158.250000 0.000000))))
(klay "D-HATCH")
(entmake (list '(0 . "LINE") (cons 8 "D-HATCH") (cons 10 '(8068.500000 160.000000 0.000000)) (cons 11 '(8069.250000 159.250000 0.000000))))
(klay "D-HATCH")
(entmake (list '(0 . "LINE") (cons 8 "D-HATCH") (cons 10 '(8068.500000 161.000000 0.000000)) (cons 11 '(8069.250000 160.250000 0.000000))))
(klay "D-HATCH")
(entmake (list '(0 . "LINE") (cons 8 "D-HATCH") (cons 10 '(8068.500000 162.000000 0.000000)) (cons 11 '(8069.250000 161.250000 0.000000))))
(klay "D-HATCH")
(entmake (list '(0 . "LINE") (cons 8 "D-HATCH") (cons 10 '(8068.500000 163.000000 0.000000)) (cons 11 '(8069.250000 162.250000 0.000000))))
(klay "D-HATCH")
(entmake (list '(0 . "LINE") (cons 8 "D-HATCH") (cons 10 '(8068.500000 164.000000 0.000000)) (cons 11 '(8069.250000 163.250000 0.000000))))
(klay "D-HATCH")
(entmake (list '(0 . "LINE") (cons 8 "D-HATCH") (cons 10 '(8068.500000 165.000000 0.000000)) (cons 11 '(8069.250000 164.250000 0.000000))))
(klay "D-HATCH")
(entmake (list '(0 . "LINE") (cons 8 "D-HATCH") (cons 10 '(8068.500000 166.000000 0.000000)) (cons 11 '(8069.250000 165.250000 0.000000))))
(klay "D-HATCH")
(entmake (list '(0 . "LINE") (cons 8 "D-HATCH") (cons 10 '(8068.500000 167.000000 0.000000)) (cons 11 '(8069.250000 166.250000 0.000000))))
(klay "D-HATCH")
(entmake (list '(0 . "LINE") (cons 8 "D-HATCH") (cons 10 '(8068.500000 168.000000 0.000000)) (cons 11 '(8069.250000 167.250000 0.000000))))
(klay "D-HATCH")
(entmake (list '(0 . "LINE") (cons 8 "D-HATCH") (cons 10 '(8068.500000 169.000000 0.000000)) (cons 11 '(8069.250000 168.250000 0.000000))))
(klay "D-HATCH")
(entmake (list '(0 . "LINE") (cons 8 "D-HATCH") (cons 10 '(8069.000000 169.500000 0.000000)) (cons 11 '(8069.250000 169.250000 0.000000))))
(klay "D-OUTLINE")
(command "_.RECTANG" '(8049.339000 141.290000 0.000000) '(8068.370000 141.790000 0.000000))
(klay "D-HATCH")
(entmake (list '(0 . "LINE") (cons 8 "D-HATCH") (cons 10 '(8049.839000 141.790000 0.000000)) (cons 11 '(8050.339000 141.290000 0.000000))))
(klay "D-HATCH")
(entmake (list '(0 . "LINE") (cons 8 "D-HATCH") (cons 10 '(8050.839000 141.790000 0.000000)) (cons 11 '(8051.339000 141.290000 0.000000))))
(klay "D-HATCH")
(entmake (list '(0 . "LINE") (cons 8 "D-HATCH") (cons 10 '(8051.839000 141.790000 0.000000)) (cons 11 '(8052.339000 141.290000 0.000000))))
(klay "D-HATCH")
(entmake (list '(0 . "LINE") (cons 8 "D-HATCH") (cons 10 '(8052.839000 141.790000 0.000000)) (cons 11 '(8053.339000 141.290000 0.000000))))
(klay "D-HATCH")
(entmake (list '(0 . "LINE") (cons 8 "D-HATCH") (cons 10 '(8053.839000 141.790000 0.000000)) (cons 11 '(8054.339000 141.290000 0.000000))))
(klay "D-HATCH")
(entmake (list '(0 . "LINE") (cons 8 "D-HATCH") (cons 10 '(8054.839000 141.790000 0.000000)) (cons 11 '(8055.339000 141.290000 0.000000))))
(klay "D-HATCH")
(entmake (list '(0 . "LINE") (cons 8 "D-HATCH") (cons 10 '(8055.839000 141.790000 0.000000)) (cons 11 '(8056.339000 141.290000 0.000000))))
(klay "D-HATCH")
(entmake (list '(0 . "LINE") (cons 8 "D-HATCH") (cons 10 '(8056.839000 141.790000 0.000000)) (cons 11 '(8057.339000 141.290000 0.000000))))
(klay "D-HATCH")
(entmake (list '(0 . "LINE") (cons 8 "D-HATCH") (cons 10 '(8057.839000 141.790000 0.000000)) (cons 11 '(8058.339000 141.290000 0.000000))))
(klay "D-HATCH")
(entmake (list '(0 . "LINE") (cons 8 "D-HATCH") (cons 10 '(8058.839000 141.790000 0.000000)) (cons 11 '(8059.339000 141.290000 0.000000))))
(klay "D-HATCH")
(entmake (list '(0 . "LINE") (cons 8 "D-HATCH") (cons 10 '(8059.839000 141.790000 0.000000)) (cons 11 '(8060.339000 141.290000 0.000000))))
(klay "D-HATCH")
(entmake (list '(0 . "LINE") (cons 8 "D-HATCH") (cons 10 '(8060.839000 141.790000 0.000000)) (cons 11 '(8061.339000 141.290000 0.000000))))
(klay "D-HATCH")
(entmake (list '(0 . "LINE") (cons 8 "D-HATCH") (cons 10 '(8061.839000 141.790000 0.000000)) (cons 11 '(8062.339000 141.290000 0.000000))))
(klay "D-HATCH")
(entmake (list '(0 . "LINE") (cons 8 "D-HATCH") (cons 10 '(8062.839000 141.790000 0.000000)) (cons 11 '(8063.339000 141.290000 0.000000))))
(klay "D-HATCH")
(entmake (list '(0 . "LINE") (cons 8 "D-HATCH") (cons 10 '(8063.839000 141.790000 0.000000)) (cons 11 '(8064.339000 141.290000 0.000000))))
(klay "D-HATCH")
(entmake (list '(0 . "LINE") (cons 8 "D-HATCH") (cons 10 '(8064.839000 141.790000 0.000000)) (cons 11 '(8065.339000 141.290000 0.000000))))
(klay "D-HATCH")
(entmake (list '(0 . "LINE") (cons 8 "D-HATCH") (cons 10 '(8065.839000 141.790000 0.000000)) (cons 11 '(8066.339000 141.290000 0.000000))))
(klay "D-HATCH")
(entmake (list '(0 . "LINE") (cons 8 "D-HATCH") (cons 10 '(8066.839000 141.790000 0.000000)) (cons 11 '(8067.339000 141.290000 0.000000))))
(klay "D-HATCH")
(entmake (list '(0 . "LINE") (cons 8 "D-HATCH") (cons 10 '(8067.839000 141.790000 0.000000)) (cons 11 '(8068.339000 141.290000 0.000000))))
(klay "D-OUTLINE")
(command "_.RECTANG" '(8049.209000 141.790000 0.000000) '(8049.709000 144.500000 0.000000))
(klay "D-HATCH")
(entmake (list '(0 . "LINE") (cons 8 "D-HATCH") (cons 10 '(8049.209000 142.790000 0.000000)) (cons 11 '(8049.709000 142.290000 0.000000))))
(klay "D-HATCH")
(entmake (list '(0 . "LINE") (cons 8 "D-HATCH") (cons 10 '(8049.209000 143.790000 0.000000)) (cons 11 '(8049.709000 143.290000 0.000000))))
(klay "D-HATCH")
(entmake (list '(0 . "LINE") (cons 8 "D-HATCH") (cons 10 '(8049.499000 144.500000 0.000000)) (cons 11 '(8049.709000 144.290000 0.000000))))
(klay "D-OUTLINE")
(command "_.RECTANG" '(8068.000000 141.790000 0.000000) '(8068.500000 168.500000 0.000000))
(klay "D-HATCH")
(entmake (list '(0 . "LINE") (cons 8 "D-HATCH") (cons 10 '(8068.000000 142.790000 0.000000)) (cons 11 '(8068.500000 142.290000 0.000000))))
(klay "D-HATCH")
(entmake (list '(0 . "LINE") (cons 8 "D-HATCH") (cons 10 '(8068.000000 143.790000 0.000000)) (cons 11 '(8068.500000 143.290000 0.000000))))
(klay "D-HATCH")
(entmake (list '(0 . "LINE") (cons 8 "D-HATCH") (cons 10 '(8068.000000 144.790000 0.000000)) (cons 11 '(8068.500000 144.290000 0.000000))))
(klay "D-HATCH")
(entmake (list '(0 . "LINE") (cons 8 "D-HATCH") (cons 10 '(8068.000000 145.790000 0.000000)) (cons 11 '(8068.500000 145.290000 0.000000))))
(klay "D-HATCH")
(entmake (list '(0 . "LINE") (cons 8 "D-HATCH") (cons 10 '(8068.000000 146.790000 0.000000)) (cons 11 '(8068.500000 146.290000 0.000000))))
(klay "D-HATCH")
(entmake (list '(0 . "LINE") (cons 8 "D-HATCH") (cons 10 '(8068.000000 147.790000 0.000000)) (cons 11 '(8068.500000 147.290000 0.000000))))
(klay "D-HATCH")
(entmake (list '(0 . "LINE") (cons 8 "D-HATCH") (cons 10 '(8068.000000 148.790000 0.000000)) (cons 11 '(8068.500000 148.290000 0.000000))))
(klay "D-HATCH")
(entmake (list '(0 . "LINE") (cons 8 "D-HATCH") (cons 10 '(8068.000000 149.790000 0.000000)) (cons 11 '(8068.500000 149.290000 0.000000))))
(klay "D-HATCH")
(entmake (list '(0 . "LINE") (cons 8 "D-HATCH") (cons 10 '(8068.000000 150.790000 0.000000)) (cons 11 '(8068.500000 150.290000 0.000000))))
(klay "D-HATCH")
(entmake (list '(0 . "LINE") (cons 8 "D-HATCH") (cons 10 '(8068.000000 151.790000 0.000000)) (cons 11 '(8068.500000 151.290000 0.000000))))
(klay "D-HATCH")
(entmake (list '(0 . "LINE") (cons 8 "D-HATCH") (cons 10 '(8068.000000 152.790000 0.000000)) (cons 11 '(8068.500000 152.290000 0.000000))))
(klay "D-HATCH")
(entmake (list '(0 . "LINE") (cons 8 "D-HATCH") (cons 10 '(8068.000000 153.790000 0.000000)) (cons 11 '(8068.500000 153.290000 0.000000))))
(klay "D-HATCH")
(entmake (list '(0 . "LINE") (cons 8 "D-HATCH") (cons 10 '(8068.000000 154.790000 0.000000)) (cons 11 '(8068.500000 154.290000 0.000000))))
(klay "D-HATCH")
(entmake (list '(0 . "LINE") (cons 8 "D-HATCH") (cons 10 '(8068.000000 155.790000 0.000000)) (cons 11 '(8068.500000 155.290000 0.000000))))
(klay "D-HATCH")
(entmake (list '(0 . "LINE") (cons 8 "D-HATCH") (cons 10 '(8068.000000 156.790000 0.000000)) (cons 11 '(8068.500000 156.290000 0.000000))))
(klay "D-HATCH")
(entmake (list '(0 . "LINE") (cons 8 "D-HATCH") (cons 10 '(8068.000000 157.790000 0.000000)) (cons 11 '(8068.500000 157.290000 0.000000))))
(klay "D-HATCH")
(entmake (list '(0 . "LINE") (cons 8 "D-HATCH") (cons 10 '(8068.000000 158.790000 0.000000)) (cons 11 '(8068.500000 158.290000 0.000000))))
(klay "D-HATCH")
(entmake (list '(0 . "LINE") (cons 8 "D-HATCH") (cons 10 '(8068.000000 159.790000 0.000000)) (cons 11 '(8068.500000 159.290000 0.000000))))
(klay "D-HATCH")
(entmake (list '(0 . "LINE") (cons 8 "D-HATCH") (cons 10 '(8068.000000 160.790000 0.000000)) (cons 11 '(8068.500000 160.290000 0.000000))))
(klay "D-HATCH")
(entmake (list '(0 . "LINE") (cons 8 "D-HATCH") (cons 10 '(8068.000000 161.790000 0.000000)) (cons 11 '(8068.500000 161.290000 0.000000))))
(klay "D-HATCH")
(entmake (list '(0 . "LINE") (cons 8 "D-HATCH") (cons 10 '(8068.000000 162.790000 0.000000)) (cons 11 '(8068.500000 162.290000 0.000000))))
(klay "D-HATCH")
(entmake (list '(0 . "LINE") (cons 8 "D-HATCH") (cons 10 '(8068.000000 163.790000 0.000000)) (cons 11 '(8068.500000 163.290000 0.000000))))
(klay "D-HATCH")
(entmake (list '(0 . "LINE") (cons 8 "D-HATCH") (cons 10 '(8068.000000 164.790000 0.000000)) (cons 11 '(8068.500000 164.290000 0.000000))))
(klay "D-HATCH")
(entmake (list '(0 . "LINE") (cons 8 "D-HATCH") (cons 10 '(8068.000000 165.790000 0.000000)) (cons 11 '(8068.500000 165.290000 0.000000))))
(klay "D-HATCH")
(entmake (list '(0 . "LINE") (cons 8 "D-HATCH") (cons 10 '(8068.000000 166.790000 0.000000)) (cons 11 '(8068.500000 166.290000 0.000000))))
(klay "D-HATCH")
(entmake (list '(0 . "LINE") (cons 8 "D-HATCH") (cons 10 '(8068.000000 167.790000 0.000000)) (cons 11 '(8068.500000 167.290000 0.000000))))
(klay "D-HATCH")
(entmake (list '(0 . "LINE") (cons 8 "D-HATCH") (cons 10 '(8068.290000 168.500000 0.000000)) (cons 11 '(8068.500000 168.290000 0.000000))))
(klay "D-FINE")
(entmake (list '(0 . "LINE") (cons 8 "D-FINE") (cons 10 '(8048.815000 140.790000 0.000000)) (cons 11 '(8068.500000 140.790000 0.000000))))
(klay "D-OUTLINE")
(command "_.RECTANG" '(8049.950000 141.790000 0.000000) '(8050.200000 165.750000 0.000000))
(klay "D-HATCH")
(entmake (list '(0 . "LINE") (cons 8 "D-HATCH") (cons 10 '(8049.950000 142.790000 0.000000)) (cons 11 '(8050.200000 142.540000 0.000000))))
(klay "D-HATCH")
(entmake (list '(0 . "LINE") (cons 8 "D-HATCH") (cons 10 '(8049.950000 143.790000 0.000000)) (cons 11 '(8050.200000 143.540000 0.000000))))
(klay "D-HATCH")
(entmake (list '(0 . "LINE") (cons 8 "D-HATCH") (cons 10 '(8049.950000 144.790000 0.000000)) (cons 11 '(8050.200000 144.540000 0.000000))))
(klay "D-HATCH")
(entmake (list '(0 . "LINE") (cons 8 "D-HATCH") (cons 10 '(8049.950000 145.790000 0.000000)) (cons 11 '(8050.200000 145.540000 0.000000))))
(klay "D-HATCH")
(entmake (list '(0 . "LINE") (cons 8 "D-HATCH") (cons 10 '(8049.950000 146.790000 0.000000)) (cons 11 '(8050.200000 146.540000 0.000000))))
(klay "D-HATCH")
(entmake (list '(0 . "LINE") (cons 8 "D-HATCH") (cons 10 '(8049.950000 147.790000 0.000000)) (cons 11 '(8050.200000 147.540000 0.000000))))
(klay "D-HATCH")
(entmake (list '(0 . "LINE") (cons 8 "D-HATCH") (cons 10 '(8049.950000 148.790000 0.000000)) (cons 11 '(8050.200000 148.540000 0.000000))))
(klay "D-HATCH")
(entmake (list '(0 . "LINE") (cons 8 "D-HATCH") (cons 10 '(8049.950000 149.790000 0.000000)) (cons 11 '(8050.200000 149.540000 0.000000))))
(klay "D-HATCH")
(entmake (list '(0 . "LINE") (cons 8 "D-HATCH") (cons 10 '(8049.950000 150.790000 0.000000)) (cons 11 '(8050.200000 150.540000 0.000000))))
(klay "D-HATCH")
(entmake (list '(0 . "LINE") (cons 8 "D-HATCH") (cons 10 '(8049.950000 151.790000 0.000000)) (cons 11 '(8050.200000 151.540000 0.000000))))
(klay "D-HATCH")
(entmake (list '(0 . "LINE") (cons 8 "D-HATCH") (cons 10 '(8049.950000 152.790000 0.000000)) (cons 11 '(8050.200000 152.540000 0.000000))))
(klay "D-HATCH")
(entmake (list '(0 . "LINE") (cons 8 "D-HATCH") (cons 10 '(8049.950000 153.790000 0.000000)) (cons 11 '(8050.200000 153.540000 0.000000))))
(klay "D-HATCH")
(entmake (list '(0 . "LINE") (cons 8 "D-HATCH") (cons 10 '(8049.950000 154.790000 0.000000)) (cons 11 '(8050.200000 154.540000 0.000000))))
(klay "D-HATCH")
(entmake (list '(0 . "LINE") (cons 8 "D-HATCH") (cons 10 '(8049.950000 155.790000 0.000000)) (cons 11 '(8050.200000 155.540000 0.000000))))
(klay "D-HATCH")
(entmake (list '(0 . "LINE") (cons 8 "D-HATCH") (cons 10 '(8049.950000 156.790000 0.000000)) (cons 11 '(8050.200000 156.540000 0.000000))))
(klay "D-HATCH")
(entmake (list '(0 . "LINE") (cons 8 "D-HATCH") (cons 10 '(8049.950000 157.790000 0.000000)) (cons 11 '(8050.200000 157.540000 0.000000))))
(klay "D-HATCH")
(entmake (list '(0 . "LINE") (cons 8 "D-HATCH") (cons 10 '(8049.950000 158.790000 0.000000)) (cons 11 '(8050.200000 158.540000 0.000000))))
(klay "D-HATCH")
(entmake (list '(0 . "LINE") (cons 8 "D-HATCH") (cons 10 '(8049.950000 159.790000 0.000000)) (cons 11 '(8050.200000 159.540000 0.000000))))
(klay "D-HATCH")
(entmake (list '(0 . "LINE") (cons 8 "D-HATCH") (cons 10 '(8049.950000 160.790000 0.000000)) (cons 11 '(8050.200000 160.540000 0.000000))))
(klay "D-HATCH")
(entmake (list '(0 . "LINE") (cons 8 "D-HATCH") (cons 10 '(8049.950000 161.790000 0.000000)) (cons 11 '(8050.200000 161.540000 0.000000))))
(klay "D-HATCH")
(entmake (list '(0 . "LINE") (cons 8 "D-HATCH") (cons 10 '(8049.950000 162.790000 0.000000)) (cons 11 '(8050.200000 162.540000 0.000000))))
(klay "D-HATCH")
(entmake (list '(0 . "LINE") (cons 8 "D-HATCH") (cons 10 '(8049.950000 163.790000 0.000000)) (cons 11 '(8050.200000 163.540000 0.000000))))
(klay "D-HATCH")
(entmake (list '(0 . "LINE") (cons 8 "D-HATCH") (cons 10 '(8049.950000 164.790000 0.000000)) (cons 11 '(8050.200000 164.540000 0.000000))))
(klay "D-HATCH")
(entmake (list '(0 . "LINE") (cons 8 "D-HATCH") (cons 10 '(8049.990000 165.750000 0.000000)) (cons 11 '(8050.200000 165.540000 0.000000))))
(klay "D-OUTLINE")
(command "_.RECTANG" '(8067.000000 141.790000 0.000000) '(8067.250000 165.750000 0.000000))
(klay "D-HATCH")
(entmake (list '(0 . "LINE") (cons 8 "D-HATCH") (cons 10 '(8067.000000 142.790000 0.000000)) (cons 11 '(8067.250000 142.540000 0.000000))))
(klay "D-HATCH")
(entmake (list '(0 . "LINE") (cons 8 "D-HATCH") (cons 10 '(8067.000000 143.790000 0.000000)) (cons 11 '(8067.250000 143.540000 0.000000))))
(klay "D-HATCH")
(entmake (list '(0 . "LINE") (cons 8 "D-HATCH") (cons 10 '(8067.000000 144.790000 0.000000)) (cons 11 '(8067.250000 144.540000 0.000000))))
(klay "D-HATCH")
(entmake (list '(0 . "LINE") (cons 8 "D-HATCH") (cons 10 '(8067.000000 145.790000 0.000000)) (cons 11 '(8067.250000 145.540000 0.000000))))
(klay "D-HATCH")
(entmake (list '(0 . "LINE") (cons 8 "D-HATCH") (cons 10 '(8067.000000 146.790000 0.000000)) (cons 11 '(8067.250000 146.540000 0.000000))))
(klay "D-HATCH")
(entmake (list '(0 . "LINE") (cons 8 "D-HATCH") (cons 10 '(8067.000000 147.790000 0.000000)) (cons 11 '(8067.250000 147.540000 0.000000))))
(klay "D-HATCH")
(entmake (list '(0 . "LINE") (cons 8 "D-HATCH") (cons 10 '(8067.000000 148.790000 0.000000)) (cons 11 '(8067.250000 148.540000 0.000000))))
(klay "D-HATCH")
(entmake (list '(0 . "LINE") (cons 8 "D-HATCH") (cons 10 '(8067.000000 149.790000 0.000000)) (cons 11 '(8067.250000 149.540000 0.000000))))
(klay "D-HATCH")
(entmake (list '(0 . "LINE") (cons 8 "D-HATCH") (cons 10 '(8067.000000 150.790000 0.000000)) (cons 11 '(8067.250000 150.540000 0.000000))))
(klay "D-HATCH")
(entmake (list '(0 . "LINE") (cons 8 "D-HATCH") (cons 10 '(8067.000000 151.790000 0.000000)) (cons 11 '(8067.250000 151.540000 0.000000))))
(klay "D-HATCH")
(entmake (list '(0 . "LINE") (cons 8 "D-HATCH") (cons 10 '(8067.000000 152.790000 0.000000)) (cons 11 '(8067.250000 152.540000 0.000000))))
(klay "D-HATCH")
(entmake (list '(0 . "LINE") (cons 8 "D-HATCH") (cons 10 '(8067.000000 153.790000 0.000000)) (cons 11 '(8067.250000 153.540000 0.000000))))
(klay "D-HATCH")
(entmake (list '(0 . "LINE") (cons 8 "D-HATCH") (cons 10 '(8067.000000 154.790000 0.000000)) (cons 11 '(8067.250000 154.540000 0.000000))))
(klay "D-HATCH")
(entmake (list '(0 . "LINE") (cons 8 "D-HATCH") (cons 10 '(8067.000000 155.790000 0.000000)) (cons 11 '(8067.250000 155.540000 0.000000))))
(klay "D-HATCH")
(entmake (list '(0 . "LINE") (cons 8 "D-HATCH") (cons 10 '(8067.000000 156.790000 0.000000)) (cons 11 '(8067.250000 156.540000 0.000000))))
(klay "D-HATCH")
(entmake (list '(0 . "LINE") (cons 8 "D-HATCH") (cons 10 '(8067.000000 157.790000 0.000000)) (cons 11 '(8067.250000 157.540000 0.000000))))
(klay "D-HATCH")
(entmake (list '(0 . "LINE") (cons 8 "D-HATCH") (cons 10 '(8067.000000 158.790000 0.000000)) (cons 11 '(8067.250000 158.540000 0.000000))))
(klay "D-HATCH")
(entmake (list '(0 . "LINE") (cons 8 "D-HATCH") (cons 10 '(8067.000000 159.790000 0.000000)) (cons 11 '(8067.250000 159.540000 0.000000))))
(klay "D-HATCH")
(entmake (list '(0 . "LINE") (cons 8 "D-HATCH") (cons 10 '(8067.000000 160.790000 0.000000)) (cons 11 '(8067.250000 160.540000 0.000000))))
(klay "D-HATCH")
(entmake (list '(0 . "LINE") (cons 8 "D-HATCH") (cons 10 '(8067.000000 161.790000 0.000000)) (cons 11 '(8067.250000 161.540000 0.000000))))
(klay "D-HATCH")
(entmake (list '(0 . "LINE") (cons 8 "D-HATCH") (cons 10 '(8067.000000 162.790000 0.000000)) (cons 11 '(8067.250000 162.540000 0.000000))))
(klay "D-HATCH")
(entmake (list '(0 . "LINE") (cons 8 "D-HATCH") (cons 10 '(8067.000000 163.790000 0.000000)) (cons 11 '(8067.250000 163.540000 0.000000))))
(klay "D-HATCH")
(entmake (list '(0 . "LINE") (cons 8 "D-HATCH") (cons 10 '(8067.000000 164.790000 0.000000)) (cons 11 '(8067.250000 164.540000 0.000000))))
(klay "D-HATCH")
(entmake (list '(0 . "LINE") (cons 8 "D-HATCH") (cons 10 '(8067.040000 165.750000 0.000000)) (cons 11 '(8067.250000 165.540000 0.000000))))
(klay "D-OUTLINE")
(command "_.RECTANG" '(8049.950000 165.500000 0.000000) '(8067.250000 165.750000 0.000000))
(klay "D-HATCH")
(entmake (list '(0 . "LINE") (cons 8 "D-HATCH") (cons 10 '(8050.700000 165.750000 0.000000)) (cons 11 '(8050.950000 165.500000 0.000000))))
(klay "D-HATCH")
(entmake (list '(0 . "LINE") (cons 8 "D-HATCH") (cons 10 '(8051.700000 165.750000 0.000000)) (cons 11 '(8051.950000 165.500000 0.000000))))
(klay "D-HATCH")
(entmake (list '(0 . "LINE") (cons 8 "D-HATCH") (cons 10 '(8052.700000 165.750000 0.000000)) (cons 11 '(8052.950000 165.500000 0.000000))))
(klay "D-HATCH")
(entmake (list '(0 . "LINE") (cons 8 "D-HATCH") (cons 10 '(8053.700000 165.750000 0.000000)) (cons 11 '(8053.950000 165.500000 0.000000))))
(klay "D-HATCH")
(entmake (list '(0 . "LINE") (cons 8 "D-HATCH") (cons 10 '(8054.700000 165.750000 0.000000)) (cons 11 '(8054.950000 165.500000 0.000000))))
(klay "D-HATCH")
(entmake (list '(0 . "LINE") (cons 8 "D-HATCH") (cons 10 '(8055.700000 165.750000 0.000000)) (cons 11 '(8055.950000 165.500000 0.000000))))
(klay "D-HATCH")
(entmake (list '(0 . "LINE") (cons 8 "D-HATCH") (cons 10 '(8056.700000 165.750000 0.000000)) (cons 11 '(8056.950000 165.500000 0.000000))))
(klay "D-HATCH")
(entmake (list '(0 . "LINE") (cons 8 "D-HATCH") (cons 10 '(8057.700000 165.750000 0.000000)) (cons 11 '(8057.950000 165.500000 0.000000))))
(klay "D-HATCH")
(entmake (list '(0 . "LINE") (cons 8 "D-HATCH") (cons 10 '(8058.700000 165.750000 0.000000)) (cons 11 '(8058.950000 165.500000 0.000000))))
(klay "D-HATCH")
(entmake (list '(0 . "LINE") (cons 8 "D-HATCH") (cons 10 '(8059.700000 165.750000 0.000000)) (cons 11 '(8059.950000 165.500000 0.000000))))
(klay "D-HATCH")
(entmake (list '(0 . "LINE") (cons 8 "D-HATCH") (cons 10 '(8060.700000 165.750000 0.000000)) (cons 11 '(8060.950000 165.500000 0.000000))))
(klay "D-HATCH")
(entmake (list '(0 . "LINE") (cons 8 "D-HATCH") (cons 10 '(8061.700000 165.750000 0.000000)) (cons 11 '(8061.950000 165.500000 0.000000))))
(klay "D-HATCH")
(entmake (list '(0 . "LINE") (cons 8 "D-HATCH") (cons 10 '(8062.700000 165.750000 0.000000)) (cons 11 '(8062.950000 165.500000 0.000000))))
(klay "D-HATCH")
(entmake (list '(0 . "LINE") (cons 8 "D-HATCH") (cons 10 '(8063.700000 165.750000 0.000000)) (cons 11 '(8063.950000 165.500000 0.000000))))
(klay "D-HATCH")
(entmake (list '(0 . "LINE") (cons 8 "D-HATCH") (cons 10 '(8064.700000 165.750000 0.000000)) (cons 11 '(8064.950000 165.500000 0.000000))))
(klay "D-HATCH")
(entmake (list '(0 . "LINE") (cons 8 "D-HATCH") (cons 10 '(8065.700000 165.750000 0.000000)) (cons 11 '(8065.950000 165.500000 0.000000))))
(klay "D-HATCH")
(entmake (list '(0 . "LINE") (cons 8 "D-HATCH") (cons 10 '(8066.700000 165.750000 0.000000)) (cons 11 '(8066.950000 165.500000 0.000000))))
(klay "D-OUTLINE")
(command "_.RECTANG" '(8050.200000 149.750000 0.000000) '(8067.000000 150.100000 0.000000))
(klay "D-HATCH")
(entmake (list '(0 . "LINE") (cons 8 "D-HATCH") (cons 10 '(8050.850000 150.100000 0.000000)) (cons 11 '(8051.200000 149.750000 0.000000))))
(klay "D-HATCH")
(entmake (list '(0 . "LINE") (cons 8 "D-HATCH") (cons 10 '(8051.850000 150.100000 0.000000)) (cons 11 '(8052.200000 149.750000 0.000000))))
(klay "D-HATCH")
(entmake (list '(0 . "LINE") (cons 8 "D-HATCH") (cons 10 '(8052.850000 150.100000 0.000000)) (cons 11 '(8053.200000 149.750000 0.000000))))
(klay "D-HATCH")
(entmake (list '(0 . "LINE") (cons 8 "D-HATCH") (cons 10 '(8053.850000 150.100000 0.000000)) (cons 11 '(8054.200000 149.750000 0.000000))))
(klay "D-HATCH")
(entmake (list '(0 . "LINE") (cons 8 "D-HATCH") (cons 10 '(8054.850000 150.100000 0.000000)) (cons 11 '(8055.200000 149.750000 0.000000))))
(klay "D-HATCH")
(entmake (list '(0 . "LINE") (cons 8 "D-HATCH") (cons 10 '(8055.850000 150.100000 0.000000)) (cons 11 '(8056.200000 149.750000 0.000000))))
(klay "D-HATCH")
(entmake (list '(0 . "LINE") (cons 8 "D-HATCH") (cons 10 '(8056.850000 150.100000 0.000000)) (cons 11 '(8057.200000 149.750000 0.000000))))
(klay "D-HATCH")
(entmake (list '(0 . "LINE") (cons 8 "D-HATCH") (cons 10 '(8057.850000 150.100000 0.000000)) (cons 11 '(8058.200000 149.750000 0.000000))))
(klay "D-HATCH")
(entmake (list '(0 . "LINE") (cons 8 "D-HATCH") (cons 10 '(8058.850000 150.100000 0.000000)) (cons 11 '(8059.200000 149.750000 0.000000))))
(klay "D-HATCH")
(entmake (list '(0 . "LINE") (cons 8 "D-HATCH") (cons 10 '(8059.850000 150.100000 0.000000)) (cons 11 '(8060.200000 149.750000 0.000000))))
(klay "D-HATCH")
(entmake (list '(0 . "LINE") (cons 8 "D-HATCH") (cons 10 '(8060.850000 150.100000 0.000000)) (cons 11 '(8061.200000 149.750000 0.000000))))
(klay "D-HATCH")
(entmake (list '(0 . "LINE") (cons 8 "D-HATCH") (cons 10 '(8061.850000 150.100000 0.000000)) (cons 11 '(8062.200000 149.750000 0.000000))))
(klay "D-HATCH")
(entmake (list '(0 . "LINE") (cons 8 "D-HATCH") (cons 10 '(8062.850000 150.100000 0.000000)) (cons 11 '(8063.200000 149.750000 0.000000))))
(klay "D-HATCH")
(entmake (list '(0 . "LINE") (cons 8 "D-HATCH") (cons 10 '(8063.850000 150.100000 0.000000)) (cons 11 '(8064.200000 149.750000 0.000000))))
(klay "D-HATCH")
(entmake (list '(0 . "LINE") (cons 8 "D-HATCH") (cons 10 '(8064.850000 150.100000 0.000000)) (cons 11 '(8065.200000 149.750000 0.000000))))
(klay "D-HATCH")
(entmake (list '(0 . "LINE") (cons 8 "D-HATCH") (cons 10 '(8065.850000 150.100000 0.000000)) (cons 11 '(8066.200000 149.750000 0.000000))))
(klay "D-HATCH")
(entmake (list '(0 . "LINE") (cons 8 "D-HATCH") (cons 10 '(8066.850000 150.100000 0.000000)) (cons 11 '(8067.000000 149.950000 0.000000))))
(klay "D-OUTLINE")
(command "_.RECTANG" '(8050.200000 157.750000 0.000000) '(8067.000000 158.100000 0.000000))
(klay "D-HATCH")
(entmake (list '(0 . "LINE") (cons 8 "D-HATCH") (cons 10 '(8050.850000 158.100000 0.000000)) (cons 11 '(8051.200000 157.750000 0.000000))))
(klay "D-HATCH")
(entmake (list '(0 . "LINE") (cons 8 "D-HATCH") (cons 10 '(8051.850000 158.100000 0.000000)) (cons 11 '(8052.200000 157.750000 0.000000))))
(klay "D-HATCH")
(entmake (list '(0 . "LINE") (cons 8 "D-HATCH") (cons 10 '(8052.850000 158.100000 0.000000)) (cons 11 '(8053.200000 157.750000 0.000000))))
(klay "D-HATCH")
(entmake (list '(0 . "LINE") (cons 8 "D-HATCH") (cons 10 '(8053.850000 158.100000 0.000000)) (cons 11 '(8054.200000 157.750000 0.000000))))
(klay "D-HATCH")
(entmake (list '(0 . "LINE") (cons 8 "D-HATCH") (cons 10 '(8054.850000 158.100000 0.000000)) (cons 11 '(8055.200000 157.750000 0.000000))))
(klay "D-HATCH")
(entmake (list '(0 . "LINE") (cons 8 "D-HATCH") (cons 10 '(8055.850000 158.100000 0.000000)) (cons 11 '(8056.200000 157.750000 0.000000))))
(klay "D-HATCH")
(entmake (list '(0 . "LINE") (cons 8 "D-HATCH") (cons 10 '(8056.850000 158.100000 0.000000)) (cons 11 '(8057.200000 157.750000 0.000000))))
(klay "D-HATCH")
(entmake (list '(0 . "LINE") (cons 8 "D-HATCH") (cons 10 '(8057.850000 158.100000 0.000000)) (cons 11 '(8058.200000 157.750000 0.000000))))
(klay "D-HATCH")
(entmake (list '(0 . "LINE") (cons 8 "D-HATCH") (cons 10 '(8058.850000 158.100000 0.000000)) (cons 11 '(8059.200000 157.750000 0.000000))))
(klay "D-HATCH")
(entmake (list '(0 . "LINE") (cons 8 "D-HATCH") (cons 10 '(8059.850000 158.100000 0.000000)) (cons 11 '(8060.200000 157.750000 0.000000))))
(klay "D-HATCH")
(entmake (list '(0 . "LINE") (cons 8 "D-HATCH") (cons 10 '(8060.850000 158.100000 0.000000)) (cons 11 '(8061.200000 157.750000 0.000000))))
(klay "D-HATCH")
(entmake (list '(0 . "LINE") (cons 8 "D-HATCH") (cons 10 '(8061.850000 158.100000 0.000000)) (cons 11 '(8062.200000 157.750000 0.000000))))
(klay "D-HATCH")
(entmake (list '(0 . "LINE") (cons 8 "D-HATCH") (cons 10 '(8062.850000 158.100000 0.000000)) (cons 11 '(8063.200000 157.750000 0.000000))))
(klay "D-HATCH")
(entmake (list '(0 . "LINE") (cons 8 "D-HATCH") (cons 10 '(8063.850000 158.100000 0.000000)) (cons 11 '(8064.200000 157.750000 0.000000))))
(klay "D-HATCH")
(entmake (list '(0 . "LINE") (cons 8 "D-HATCH") (cons 10 '(8064.850000 158.100000 0.000000)) (cons 11 '(8065.200000 157.750000 0.000000))))
(klay "D-HATCH")
(entmake (list '(0 . "LINE") (cons 8 "D-HATCH") (cons 10 '(8065.850000 158.100000 0.000000)) (cons 11 '(8066.200000 157.750000 0.000000))))
(klay "D-HATCH")
(entmake (list '(0 . "LINE") (cons 8 "D-HATCH") (cons 10 '(8066.850000 158.100000 0.000000)) (cons 11 '(8067.000000 157.950000 0.000000))))
(klay "D-OUTLINE")
(command "_.RECTANG" '(8049.950000 149.600000 0.000000) '(8050.450000 149.750000 0.000000))
(klay "D-OUTLINE")
(command "_.RECTANG" '(8066.750000 149.600000 0.000000) '(8067.250000 149.750000 0.000000))
(klay "D-OUTLINE")
(command "_.RECTANG" '(8049.950000 157.600000 0.000000) '(8050.450000 157.750000 0.000000))
(klay "D-OUTLINE")
(command "_.RECTANG" '(8066.750000 157.600000 0.000000) '(8067.250000 157.750000 0.000000))
(klay "D-TEXT")
(entmake (list '(0 . "TEXT") (cons 8 "D-TEXT") (cons 10 '(8044.000000 127.000000 0.000000)) (cons 40 1.05) (cons 1 "SECTION / STUDY") '(7 . "KITCHEN") '(50 . 0.0)))
(klay "D-TEXT")
(entmake (list '(0 . "TEXT") (cons 8 "D-TEXT") (cons 10 '(8044.000000 123.000000 0.000000)) (cons 40 1.05) (cons 1 "Runners by supplier") '(7 . "KITCHEN") '(50 . 0.0)))
(klay "D-OUTLINE")
(command "_.RECTANG" '(8076.000000 135.000000 0.000000) '(8086.000000 169.500000 0.000000))
(klay "D-OUTLINE")
(command "_.RECTANG" '(8076.000000 139.000000 0.000000) '(8086.000000 169.500000 0.000000))
(klay "D-OUTLINE")
(command "_.RECTANG" '(8078.323000 167.962200 0.000000) '(8083.677000 168.237800 0.000000))
(klay "D-DIMS")
(command "_.DIMLINEAR" '(8076.000000 169.500000 0.000000) '(8086.000000 169.500000 0.000000) "_H" '(8081.000000 177.000000 0.000000))
(klay "D-TITLE")
(entmake (list '(0 . "TEXT") (cons 8 "D-TITLE") (cons 10 '(8072.000000 127.000000 0.000000)) (cons 40 1.15) (cons 1 "UTENSIL / RIGHT OF RANGE") '(7 . "KITCHEN") '(50 . 0.0)))
(klay "D-TEXT")
(entmake (list '(0 . "TEXT") (cons 8 "D-TEXT") (cons 10 '(8072.000000 123.000000 0.000000)) (cons 40 1.1) (cons 1 "FULL-HEIGHT PULLOUT") '(7 . "KITCHEN") '(50 . 0.0)))
(klay "D-OUTLINE")
(command "_.RECTANG" '(8096.000000 135.000000 0.000000) '(8120.250000 169.500000 0.000000))
(klay "D-OUTLINE")
(command "_.RECTANG" '(8119.500000 139.000000 0.000000) '(8120.250000 169.500000 0.000000))
(klay "D-HATCH")
(entmake (list '(0 . "LINE") (cons 8 "D-HATCH") (cons 10 '(8119.500000 140.000000 0.000000)) (cons 11 '(8120.250000 139.250000 0.000000))))
(klay "D-HATCH")
(entmake (list '(0 . "LINE") (cons 8 "D-HATCH") (cons 10 '(8119.500000 141.000000 0.000000)) (cons 11 '(8120.250000 140.250000 0.000000))))
(klay "D-HATCH")
(entmake (list '(0 . "LINE") (cons 8 "D-HATCH") (cons 10 '(8119.500000 142.000000 0.000000)) (cons 11 '(8120.250000 141.250000 0.000000))))
(klay "D-HATCH")
(entmake (list '(0 . "LINE") (cons 8 "D-HATCH") (cons 10 '(8119.500000 143.000000 0.000000)) (cons 11 '(8120.250000 142.250000 0.000000))))
(klay "D-HATCH")
(entmake (list '(0 . "LINE") (cons 8 "D-HATCH") (cons 10 '(8119.500000 144.000000 0.000000)) (cons 11 '(8120.250000 143.250000 0.000000))))
(klay "D-HATCH")
(entmake (list '(0 . "LINE") (cons 8 "D-HATCH") (cons 10 '(8119.500000 145.000000 0.000000)) (cons 11 '(8120.250000 144.250000 0.000000))))
(klay "D-HATCH")
(entmake (list '(0 . "LINE") (cons 8 "D-HATCH") (cons 10 '(8119.500000 146.000000 0.000000)) (cons 11 '(8120.250000 145.250000 0.000000))))
(klay "D-HATCH")
(entmake (list '(0 . "LINE") (cons 8 "D-HATCH") (cons 10 '(8119.500000 147.000000 0.000000)) (cons 11 '(8120.250000 146.250000 0.000000))))
(klay "D-HATCH")
(entmake (list '(0 . "LINE") (cons 8 "D-HATCH") (cons 10 '(8119.500000 148.000000 0.000000)) (cons 11 '(8120.250000 147.250000 0.000000))))
(klay "D-HATCH")
(entmake (list '(0 . "LINE") (cons 8 "D-HATCH") (cons 10 '(8119.500000 149.000000 0.000000)) (cons 11 '(8120.250000 148.250000 0.000000))))
(klay "D-HATCH")
(entmake (list '(0 . "LINE") (cons 8 "D-HATCH") (cons 10 '(8119.500000 150.000000 0.000000)) (cons 11 '(8120.250000 149.250000 0.000000))))
(klay "D-HATCH")
(entmake (list '(0 . "LINE") (cons 8 "D-HATCH") (cons 10 '(8119.500000 151.000000 0.000000)) (cons 11 '(8120.250000 150.250000 0.000000))))
(klay "D-HATCH")
(entmake (list '(0 . "LINE") (cons 8 "D-HATCH") (cons 10 '(8119.500000 152.000000 0.000000)) (cons 11 '(8120.250000 151.250000 0.000000))))
(klay "D-HATCH")
(entmake (list '(0 . "LINE") (cons 8 "D-HATCH") (cons 10 '(8119.500000 153.000000 0.000000)) (cons 11 '(8120.250000 152.250000 0.000000))))
(klay "D-HATCH")
(entmake (list '(0 . "LINE") (cons 8 "D-HATCH") (cons 10 '(8119.500000 154.000000 0.000000)) (cons 11 '(8120.250000 153.250000 0.000000))))
(klay "D-HATCH")
(entmake (list '(0 . "LINE") (cons 8 "D-HATCH") (cons 10 '(8119.500000 155.000000 0.000000)) (cons 11 '(8120.250000 154.250000 0.000000))))
(klay "D-HATCH")
(entmake (list '(0 . "LINE") (cons 8 "D-HATCH") (cons 10 '(8119.500000 156.000000 0.000000)) (cons 11 '(8120.250000 155.250000 0.000000))))
(klay "D-HATCH")
(entmake (list '(0 . "LINE") (cons 8 "D-HATCH") (cons 10 '(8119.500000 157.000000 0.000000)) (cons 11 '(8120.250000 156.250000 0.000000))))
(klay "D-HATCH")
(entmake (list '(0 . "LINE") (cons 8 "D-HATCH") (cons 10 '(8119.500000 158.000000 0.000000)) (cons 11 '(8120.250000 157.250000 0.000000))))
(klay "D-HATCH")
(entmake (list '(0 . "LINE") (cons 8 "D-HATCH") (cons 10 '(8119.500000 159.000000 0.000000)) (cons 11 '(8120.250000 158.250000 0.000000))))
(klay "D-HATCH")
(entmake (list '(0 . "LINE") (cons 8 "D-HATCH") (cons 10 '(8119.500000 160.000000 0.000000)) (cons 11 '(8120.250000 159.250000 0.000000))))
(klay "D-HATCH")
(entmake (list '(0 . "LINE") (cons 8 "D-HATCH") (cons 10 '(8119.500000 161.000000 0.000000)) (cons 11 '(8120.250000 160.250000 0.000000))))
(klay "D-HATCH")
(entmake (list '(0 . "LINE") (cons 8 "D-HATCH") (cons 10 '(8119.500000 162.000000 0.000000)) (cons 11 '(8120.250000 161.250000 0.000000))))
(klay "D-HATCH")
(entmake (list '(0 . "LINE") (cons 8 "D-HATCH") (cons 10 '(8119.500000 163.000000 0.000000)) (cons 11 '(8120.250000 162.250000 0.000000))))
(klay "D-HATCH")
(entmake (list '(0 . "LINE") (cons 8 "D-HATCH") (cons 10 '(8119.500000 164.000000 0.000000)) (cons 11 '(8120.250000 163.250000 0.000000))))
(klay "D-HATCH")
(entmake (list '(0 . "LINE") (cons 8 "D-HATCH") (cons 10 '(8119.500000 165.000000 0.000000)) (cons 11 '(8120.250000 164.250000 0.000000))))
(klay "D-HATCH")
(entmake (list '(0 . "LINE") (cons 8 "D-HATCH") (cons 10 '(8119.500000 166.000000 0.000000)) (cons 11 '(8120.250000 165.250000 0.000000))))
(klay "D-HATCH")
(entmake (list '(0 . "LINE") (cons 8 "D-HATCH") (cons 10 '(8119.500000 167.000000 0.000000)) (cons 11 '(8120.250000 166.250000 0.000000))))
(klay "D-HATCH")
(entmake (list '(0 . "LINE") (cons 8 "D-HATCH") (cons 10 '(8119.500000 168.000000 0.000000)) (cons 11 '(8120.250000 167.250000 0.000000))))
(klay "D-HATCH")
(entmake (list '(0 . "LINE") (cons 8 "D-HATCH") (cons 10 '(8119.500000 169.000000 0.000000)) (cons 11 '(8120.250000 168.250000 0.000000))))
(klay "D-HATCH")
(entmake (list '(0 . "LINE") (cons 8 "D-HATCH") (cons 10 '(8120.000000 169.500000 0.000000)) (cons 11 '(8120.250000 169.250000 0.000000))))
(klay "D-OUTLINE")
(command "_.RECTANG" '(8100.339000 141.290000 0.000000) '(8119.370000 141.790000 0.000000))
(klay "D-HATCH")
(entmake (list '(0 . "LINE") (cons 8 "D-HATCH") (cons 10 '(8100.839000 141.790000 0.000000)) (cons 11 '(8101.339000 141.290000 0.000000))))
(klay "D-HATCH")
(entmake (list '(0 . "LINE") (cons 8 "D-HATCH") (cons 10 '(8101.839000 141.790000 0.000000)) (cons 11 '(8102.339000 141.290000 0.000000))))
(klay "D-HATCH")
(entmake (list '(0 . "LINE") (cons 8 "D-HATCH") (cons 10 '(8102.839000 141.790000 0.000000)) (cons 11 '(8103.339000 141.290000 0.000000))))
(klay "D-HATCH")
(entmake (list '(0 . "LINE") (cons 8 "D-HATCH") (cons 10 '(8103.839000 141.790000 0.000000)) (cons 11 '(8104.339000 141.290000 0.000000))))
(klay "D-HATCH")
(entmake (list '(0 . "LINE") (cons 8 "D-HATCH") (cons 10 '(8104.839000 141.790000 0.000000)) (cons 11 '(8105.339000 141.290000 0.000000))))
(klay "D-HATCH")
(entmake (list '(0 . "LINE") (cons 8 "D-HATCH") (cons 10 '(8105.839000 141.790000 0.000000)) (cons 11 '(8106.339000 141.290000 0.000000))))
(klay "D-HATCH")
(entmake (list '(0 . "LINE") (cons 8 "D-HATCH") (cons 10 '(8106.839000 141.790000 0.000000)) (cons 11 '(8107.339000 141.290000 0.000000))))
(klay "D-HATCH")
(entmake (list '(0 . "LINE") (cons 8 "D-HATCH") (cons 10 '(8107.839000 141.790000 0.000000)) (cons 11 '(8108.339000 141.290000 0.000000))))
(klay "D-HATCH")
(entmake (list '(0 . "LINE") (cons 8 "D-HATCH") (cons 10 '(8108.839000 141.790000 0.000000)) (cons 11 '(8109.339000 141.290000 0.000000))))
(klay "D-HATCH")
(entmake (list '(0 . "LINE") (cons 8 "D-HATCH") (cons 10 '(8109.839000 141.790000 0.000000)) (cons 11 '(8110.339000 141.290000 0.000000))))
(klay "D-HATCH")
(entmake (list '(0 . "LINE") (cons 8 "D-HATCH") (cons 10 '(8110.839000 141.790000 0.000000)) (cons 11 '(8111.339000 141.290000 0.000000))))
(klay "D-HATCH")
(entmake (list '(0 . "LINE") (cons 8 "D-HATCH") (cons 10 '(8111.839000 141.790000 0.000000)) (cons 11 '(8112.339000 141.290000 0.000000))))
(klay "D-HATCH")
(entmake (list '(0 . "LINE") (cons 8 "D-HATCH") (cons 10 '(8112.839000 141.790000 0.000000)) (cons 11 '(8113.339000 141.290000 0.000000))))
(klay "D-HATCH")
(entmake (list '(0 . "LINE") (cons 8 "D-HATCH") (cons 10 '(8113.839000 141.790000 0.000000)) (cons 11 '(8114.339000 141.290000 0.000000))))
(klay "D-HATCH")
(entmake (list '(0 . "LINE") (cons 8 "D-HATCH") (cons 10 '(8114.839000 141.790000 0.000000)) (cons 11 '(8115.339000 141.290000 0.000000))))
(klay "D-HATCH")
(entmake (list '(0 . "LINE") (cons 8 "D-HATCH") (cons 10 '(8115.839000 141.790000 0.000000)) (cons 11 '(8116.339000 141.290000 0.000000))))
(klay "D-HATCH")
(entmake (list '(0 . "LINE") (cons 8 "D-HATCH") (cons 10 '(8116.839000 141.790000 0.000000)) (cons 11 '(8117.339000 141.290000 0.000000))))
(klay "D-HATCH")
(entmake (list '(0 . "LINE") (cons 8 "D-HATCH") (cons 10 '(8117.839000 141.790000 0.000000)) (cons 11 '(8118.339000 141.290000 0.000000))))
(klay "D-HATCH")
(entmake (list '(0 . "LINE") (cons 8 "D-HATCH") (cons 10 '(8118.839000 141.790000 0.000000)) (cons 11 '(8119.339000 141.290000 0.000000))))
(klay "D-OUTLINE")
(command "_.RECTANG" '(8100.209000 141.790000 0.000000) '(8100.709000 144.500000 0.000000))
(klay "D-HATCH")
(entmake (list '(0 . "LINE") (cons 8 "D-HATCH") (cons 10 '(8100.209000 142.790000 0.000000)) (cons 11 '(8100.709000 142.290000 0.000000))))
(klay "D-HATCH")
(entmake (list '(0 . "LINE") (cons 8 "D-HATCH") (cons 10 '(8100.209000 143.790000 0.000000)) (cons 11 '(8100.709000 143.290000 0.000000))))
(klay "D-HATCH")
(entmake (list '(0 . "LINE") (cons 8 "D-HATCH") (cons 10 '(8100.499000 144.500000 0.000000)) (cons 11 '(8100.709000 144.290000 0.000000))))
(klay "D-OUTLINE")
(command "_.RECTANG" '(8119.000000 141.790000 0.000000) '(8119.500000 168.500000 0.000000))
(klay "D-HATCH")
(entmake (list '(0 . "LINE") (cons 8 "D-HATCH") (cons 10 '(8119.000000 142.790000 0.000000)) (cons 11 '(8119.500000 142.290000 0.000000))))
(klay "D-HATCH")
(entmake (list '(0 . "LINE") (cons 8 "D-HATCH") (cons 10 '(8119.000000 143.790000 0.000000)) (cons 11 '(8119.500000 143.290000 0.000000))))
(klay "D-HATCH")
(entmake (list '(0 . "LINE") (cons 8 "D-HATCH") (cons 10 '(8119.000000 144.790000 0.000000)) (cons 11 '(8119.500000 144.290000 0.000000))))
(klay "D-HATCH")
(entmake (list '(0 . "LINE") (cons 8 "D-HATCH") (cons 10 '(8119.000000 145.790000 0.000000)) (cons 11 '(8119.500000 145.290000 0.000000))))
(klay "D-HATCH")
(entmake (list '(0 . "LINE") (cons 8 "D-HATCH") (cons 10 '(8119.000000 146.790000 0.000000)) (cons 11 '(8119.500000 146.290000 0.000000))))
(klay "D-HATCH")
(entmake (list '(0 . "LINE") (cons 8 "D-HATCH") (cons 10 '(8119.000000 147.790000 0.000000)) (cons 11 '(8119.500000 147.290000 0.000000))))
(klay "D-HATCH")
(entmake (list '(0 . "LINE") (cons 8 "D-HATCH") (cons 10 '(8119.000000 148.790000 0.000000)) (cons 11 '(8119.500000 148.290000 0.000000))))
(klay "D-HATCH")
(entmake (list '(0 . "LINE") (cons 8 "D-HATCH") (cons 10 '(8119.000000 149.790000 0.000000)) (cons 11 '(8119.500000 149.290000 0.000000))))
(klay "D-HATCH")
(entmake (list '(0 . "LINE") (cons 8 "D-HATCH") (cons 10 '(8119.000000 150.790000 0.000000)) (cons 11 '(8119.500000 150.290000 0.000000))))
(klay "D-HATCH")
(entmake (list '(0 . "LINE") (cons 8 "D-HATCH") (cons 10 '(8119.000000 151.790000 0.000000)) (cons 11 '(8119.500000 151.290000 0.000000))))
(klay "D-HATCH")
(entmake (list '(0 . "LINE") (cons 8 "D-HATCH") (cons 10 '(8119.000000 152.790000 0.000000)) (cons 11 '(8119.500000 152.290000 0.000000))))
(klay "D-HATCH")
(entmake (list '(0 . "LINE") (cons 8 "D-HATCH") (cons 10 '(8119.000000 153.790000 0.000000)) (cons 11 '(8119.500000 153.290000 0.000000))))
(klay "D-HATCH")
(entmake (list '(0 . "LINE") (cons 8 "D-HATCH") (cons 10 '(8119.000000 154.790000 0.000000)) (cons 11 '(8119.500000 154.290000 0.000000))))
(klay "D-HATCH")
(entmake (list '(0 . "LINE") (cons 8 "D-HATCH") (cons 10 '(8119.000000 155.790000 0.000000)) (cons 11 '(8119.500000 155.290000 0.000000))))
(klay "D-HATCH")
(entmake (list '(0 . "LINE") (cons 8 "D-HATCH") (cons 10 '(8119.000000 156.790000 0.000000)) (cons 11 '(8119.500000 156.290000 0.000000))))
(klay "D-HATCH")
(entmake (list '(0 . "LINE") (cons 8 "D-HATCH") (cons 10 '(8119.000000 157.790000 0.000000)) (cons 11 '(8119.500000 157.290000 0.000000))))
(klay "D-HATCH")
(entmake (list '(0 . "LINE") (cons 8 "D-HATCH") (cons 10 '(8119.000000 158.790000 0.000000)) (cons 11 '(8119.500000 158.290000 0.000000))))
(klay "D-HATCH")
(entmake (list '(0 . "LINE") (cons 8 "D-HATCH") (cons 10 '(8119.000000 159.790000 0.000000)) (cons 11 '(8119.500000 159.290000 0.000000))))
(klay "D-HATCH")
(entmake (list '(0 . "LINE") (cons 8 "D-HATCH") (cons 10 '(8119.000000 160.790000 0.000000)) (cons 11 '(8119.500000 160.290000 0.000000))))
(klay "D-HATCH")
(entmake (list '(0 . "LINE") (cons 8 "D-HATCH") (cons 10 '(8119.000000 161.790000 0.000000)) (cons 11 '(8119.500000 161.290000 0.000000))))
(klay "D-HATCH")
(entmake (list '(0 . "LINE") (cons 8 "D-HATCH") (cons 10 '(8119.000000 162.790000 0.000000)) (cons 11 '(8119.500000 162.290000 0.000000))))
(klay "D-HATCH")
(entmake (list '(0 . "LINE") (cons 8 "D-HATCH") (cons 10 '(8119.000000 163.790000 0.000000)) (cons 11 '(8119.500000 163.290000 0.000000))))
(klay "D-HATCH")
(entmake (list '(0 . "LINE") (cons 8 "D-HATCH") (cons 10 '(8119.000000 164.790000 0.000000)) (cons 11 '(8119.500000 164.290000 0.000000))))
(klay "D-HATCH")
(entmake (list '(0 . "LINE") (cons 8 "D-HATCH") (cons 10 '(8119.000000 165.790000 0.000000)) (cons 11 '(8119.500000 165.290000 0.000000))))
(klay "D-HATCH")
(entmake (list '(0 . "LINE") (cons 8 "D-HATCH") (cons 10 '(8119.000000 166.790000 0.000000)) (cons 11 '(8119.500000 166.290000 0.000000))))
(klay "D-HATCH")
(entmake (list '(0 . "LINE") (cons 8 "D-HATCH") (cons 10 '(8119.000000 167.790000 0.000000)) (cons 11 '(8119.500000 167.290000 0.000000))))
(klay "D-HATCH")
(entmake (list '(0 . "LINE") (cons 8 "D-HATCH") (cons 10 '(8119.290000 168.500000 0.000000)) (cons 11 '(8119.500000 168.290000 0.000000))))
(klay "D-FINE")
(entmake (list '(0 . "LINE") (cons 8 "D-FINE") (cons 10 '(8099.815000 140.790000 0.000000)) (cons 11 '(8119.500000 140.790000 0.000000))))
(klay "D-OUTLINE")
(command "_.RECTANG" '(8100.950000 141.790000 0.000000) '(8101.200000 165.750000 0.000000))
(klay "D-HATCH")
(entmake (list '(0 . "LINE") (cons 8 "D-HATCH") (cons 10 '(8100.950000 142.790000 0.000000)) (cons 11 '(8101.200000 142.540000 0.000000))))
(klay "D-HATCH")
(entmake (list '(0 . "LINE") (cons 8 "D-HATCH") (cons 10 '(8100.950000 143.790000 0.000000)) (cons 11 '(8101.200000 143.540000 0.000000))))
(klay "D-HATCH")
(entmake (list '(0 . "LINE") (cons 8 "D-HATCH") (cons 10 '(8100.950000 144.790000 0.000000)) (cons 11 '(8101.200000 144.540000 0.000000))))
(klay "D-HATCH")
(entmake (list '(0 . "LINE") (cons 8 "D-HATCH") (cons 10 '(8100.950000 145.790000 0.000000)) (cons 11 '(8101.200000 145.540000 0.000000))))
(klay "D-HATCH")
(entmake (list '(0 . "LINE") (cons 8 "D-HATCH") (cons 10 '(8100.950000 146.790000 0.000000)) (cons 11 '(8101.200000 146.540000 0.000000))))
(klay "D-HATCH")
(entmake (list '(0 . "LINE") (cons 8 "D-HATCH") (cons 10 '(8100.950000 147.790000 0.000000)) (cons 11 '(8101.200000 147.540000 0.000000))))
(klay "D-HATCH")
(entmake (list '(0 . "LINE") (cons 8 "D-HATCH") (cons 10 '(8100.950000 148.790000 0.000000)) (cons 11 '(8101.200000 148.540000 0.000000))))
(klay "D-HATCH")
(entmake (list '(0 . "LINE") (cons 8 "D-HATCH") (cons 10 '(8100.950000 149.790000 0.000000)) (cons 11 '(8101.200000 149.540000 0.000000))))
(klay "D-HATCH")
(entmake (list '(0 . "LINE") (cons 8 "D-HATCH") (cons 10 '(8100.950000 150.790000 0.000000)) (cons 11 '(8101.200000 150.540000 0.000000))))
(klay "D-HATCH")
(entmake (list '(0 . "LINE") (cons 8 "D-HATCH") (cons 10 '(8100.950000 151.790000 0.000000)) (cons 11 '(8101.200000 151.540000 0.000000))))
(klay "D-HATCH")
(entmake (list '(0 . "LINE") (cons 8 "D-HATCH") (cons 10 '(8100.950000 152.790000 0.000000)) (cons 11 '(8101.200000 152.540000 0.000000))))
(klay "D-HATCH")
(entmake (list '(0 . "LINE") (cons 8 "D-HATCH") (cons 10 '(8100.950000 153.790000 0.000000)) (cons 11 '(8101.200000 153.540000 0.000000))))
(klay "D-HATCH")
(entmake (list '(0 . "LINE") (cons 8 "D-HATCH") (cons 10 '(8100.950000 154.790000 0.000000)) (cons 11 '(8101.200000 154.540000 0.000000))))
(klay "D-HATCH")
(entmake (list '(0 . "LINE") (cons 8 "D-HATCH") (cons 10 '(8100.950000 155.790000 0.000000)) (cons 11 '(8101.200000 155.540000 0.000000))))
(klay "D-HATCH")
(entmake (list '(0 . "LINE") (cons 8 "D-HATCH") (cons 10 '(8100.950000 156.790000 0.000000)) (cons 11 '(8101.200000 156.540000 0.000000))))
(klay "D-HATCH")
(entmake (list '(0 . "LINE") (cons 8 "D-HATCH") (cons 10 '(8100.950000 157.790000 0.000000)) (cons 11 '(8101.200000 157.540000 0.000000))))
(klay "D-HATCH")
(entmake (list '(0 . "LINE") (cons 8 "D-HATCH") (cons 10 '(8100.950000 158.790000 0.000000)) (cons 11 '(8101.200000 158.540000 0.000000))))
(klay "D-HATCH")
(entmake (list '(0 . "LINE") (cons 8 "D-HATCH") (cons 10 '(8100.950000 159.790000 0.000000)) (cons 11 '(8101.200000 159.540000 0.000000))))
(klay "D-HATCH")
(entmake (list '(0 . "LINE") (cons 8 "D-HATCH") (cons 10 '(8100.950000 160.790000 0.000000)) (cons 11 '(8101.200000 160.540000 0.000000))))
(klay "D-HATCH")
(entmake (list '(0 . "LINE") (cons 8 "D-HATCH") (cons 10 '(8100.950000 161.790000 0.000000)) (cons 11 '(8101.200000 161.540000 0.000000))))
(klay "D-HATCH")
(entmake (list '(0 . "LINE") (cons 8 "D-HATCH") (cons 10 '(8100.950000 162.790000 0.000000)) (cons 11 '(8101.200000 162.540000 0.000000))))
(klay "D-HATCH")
(entmake (list '(0 . "LINE") (cons 8 "D-HATCH") (cons 10 '(8100.950000 163.790000 0.000000)) (cons 11 '(8101.200000 163.540000 0.000000))))
(klay "D-HATCH")
(entmake (list '(0 . "LINE") (cons 8 "D-HATCH") (cons 10 '(8100.950000 164.790000 0.000000)) (cons 11 '(8101.200000 164.540000 0.000000))))
(klay "D-HATCH")
(entmake (list '(0 . "LINE") (cons 8 "D-HATCH") (cons 10 '(8100.990000 165.750000 0.000000)) (cons 11 '(8101.200000 165.540000 0.000000))))
(klay "D-OUTLINE")
(command "_.RECTANG" '(8118.000000 141.790000 0.000000) '(8118.250000 165.750000 0.000000))
(klay "D-HATCH")
(entmake (list '(0 . "LINE") (cons 8 "D-HATCH") (cons 10 '(8118.000000 142.790000 0.000000)) (cons 11 '(8118.250000 142.540000 0.000000))))
(klay "D-HATCH")
(entmake (list '(0 . "LINE") (cons 8 "D-HATCH") (cons 10 '(8118.000000 143.790000 0.000000)) (cons 11 '(8118.250000 143.540000 0.000000))))
(klay "D-HATCH")
(entmake (list '(0 . "LINE") (cons 8 "D-HATCH") (cons 10 '(8118.000000 144.790000 0.000000)) (cons 11 '(8118.250000 144.540000 0.000000))))
(klay "D-HATCH")
(entmake (list '(0 . "LINE") (cons 8 "D-HATCH") (cons 10 '(8118.000000 145.790000 0.000000)) (cons 11 '(8118.250000 145.540000 0.000000))))
(klay "D-HATCH")
(entmake (list '(0 . "LINE") (cons 8 "D-HATCH") (cons 10 '(8118.000000 146.790000 0.000000)) (cons 11 '(8118.250000 146.540000 0.000000))))
(klay "D-HATCH")
(entmake (list '(0 . "LINE") (cons 8 "D-HATCH") (cons 10 '(8118.000000 147.790000 0.000000)) (cons 11 '(8118.250000 147.540000 0.000000))))
(klay "D-HATCH")
(entmake (list '(0 . "LINE") (cons 8 "D-HATCH") (cons 10 '(8118.000000 148.790000 0.000000)) (cons 11 '(8118.250000 148.540000 0.000000))))
(klay "D-HATCH")
(entmake (list '(0 . "LINE") (cons 8 "D-HATCH") (cons 10 '(8118.000000 149.790000 0.000000)) (cons 11 '(8118.250000 149.540000 0.000000))))
(klay "D-HATCH")
(entmake (list '(0 . "LINE") (cons 8 "D-HATCH") (cons 10 '(8118.000000 150.790000 0.000000)) (cons 11 '(8118.250000 150.540000 0.000000))))
(klay "D-HATCH")
(entmake (list '(0 . "LINE") (cons 8 "D-HATCH") (cons 10 '(8118.000000 151.790000 0.000000)) (cons 11 '(8118.250000 151.540000 0.000000))))
(klay "D-HATCH")
(entmake (list '(0 . "LINE") (cons 8 "D-HATCH") (cons 10 '(8118.000000 152.790000 0.000000)) (cons 11 '(8118.250000 152.540000 0.000000))))
(klay "D-HATCH")
(entmake (list '(0 . "LINE") (cons 8 "D-HATCH") (cons 10 '(8118.000000 153.790000 0.000000)) (cons 11 '(8118.250000 153.540000 0.000000))))
(klay "D-HATCH")
(entmake (list '(0 . "LINE") (cons 8 "D-HATCH") (cons 10 '(8118.000000 154.790000 0.000000)) (cons 11 '(8118.250000 154.540000 0.000000))))
(klay "D-HATCH")
(entmake (list '(0 . "LINE") (cons 8 "D-HATCH") (cons 10 '(8118.000000 155.790000 0.000000)) (cons 11 '(8118.250000 155.540000 0.000000))))
(klay "D-HATCH")
(entmake (list '(0 . "LINE") (cons 8 "D-HATCH") (cons 10 '(8118.000000 156.790000 0.000000)) (cons 11 '(8118.250000 156.540000 0.000000))))
(klay "D-HATCH")
(entmake (list '(0 . "LINE") (cons 8 "D-HATCH") (cons 10 '(8118.000000 157.790000 0.000000)) (cons 11 '(8118.250000 157.540000 0.000000))))
(klay "D-HATCH")
(entmake (list '(0 . "LINE") (cons 8 "D-HATCH") (cons 10 '(8118.000000 158.790000 0.000000)) (cons 11 '(8118.250000 158.540000 0.000000))))
(klay "D-HATCH")
(entmake (list '(0 . "LINE") (cons 8 "D-HATCH") (cons 10 '(8118.000000 159.790000 0.000000)) (cons 11 '(8118.250000 159.540000 0.000000))))
(klay "D-HATCH")
(entmake (list '(0 . "LINE") (cons 8 "D-HATCH") (cons 10 '(8118.000000 160.790000 0.000000)) (cons 11 '(8118.250000 160.540000 0.000000))))
(klay "D-HATCH")
(entmake (list '(0 . "LINE") (cons 8 "D-HATCH") (cons 10 '(8118.000000 161.790000 0.000000)) (cons 11 '(8118.250000 161.540000 0.000000))))
(klay "D-HATCH")
(entmake (list '(0 . "LINE") (cons 8 "D-HATCH") (cons 10 '(8118.000000 162.790000 0.000000)) (cons 11 '(8118.250000 162.540000 0.000000))))
(klay "D-HATCH")
(entmake (list '(0 . "LINE") (cons 8 "D-HATCH") (cons 10 '(8118.000000 163.790000 0.000000)) (cons 11 '(8118.250000 163.540000 0.000000))))
(klay "D-HATCH")
(entmake (list '(0 . "LINE") (cons 8 "D-HATCH") (cons 10 '(8118.000000 164.790000 0.000000)) (cons 11 '(8118.250000 164.540000 0.000000))))
(klay "D-HATCH")
(entmake (list '(0 . "LINE") (cons 8 "D-HATCH") (cons 10 '(8118.040000 165.750000 0.000000)) (cons 11 '(8118.250000 165.540000 0.000000))))
(klay "D-OUTLINE")
(command "_.RECTANG" '(8100.950000 165.500000 0.000000) '(8118.250000 165.750000 0.000000))
(klay "D-HATCH")
(entmake (list '(0 . "LINE") (cons 8 "D-HATCH") (cons 10 '(8101.700000 165.750000 0.000000)) (cons 11 '(8101.950000 165.500000 0.000000))))
(klay "D-HATCH")
(entmake (list '(0 . "LINE") (cons 8 "D-HATCH") (cons 10 '(8102.700000 165.750000 0.000000)) (cons 11 '(8102.950000 165.500000 0.000000))))
(klay "D-HATCH")
(entmake (list '(0 . "LINE") (cons 8 "D-HATCH") (cons 10 '(8103.700000 165.750000 0.000000)) (cons 11 '(8103.950000 165.500000 0.000000))))
(klay "D-HATCH")
(entmake (list '(0 . "LINE") (cons 8 "D-HATCH") (cons 10 '(8104.700000 165.750000 0.000000)) (cons 11 '(8104.950000 165.500000 0.000000))))
(klay "D-HATCH")
(entmake (list '(0 . "LINE") (cons 8 "D-HATCH") (cons 10 '(8105.700000 165.750000 0.000000)) (cons 11 '(8105.950000 165.500000 0.000000))))
(klay "D-HATCH")
(entmake (list '(0 . "LINE") (cons 8 "D-HATCH") (cons 10 '(8106.700000 165.750000 0.000000)) (cons 11 '(8106.950000 165.500000 0.000000))))
(klay "D-HATCH")
(entmake (list '(0 . "LINE") (cons 8 "D-HATCH") (cons 10 '(8107.700000 165.750000 0.000000)) (cons 11 '(8107.950000 165.500000 0.000000))))
(klay "D-HATCH")
(entmake (list '(0 . "LINE") (cons 8 "D-HATCH") (cons 10 '(8108.700000 165.750000 0.000000)) (cons 11 '(8108.950000 165.500000 0.000000))))
(klay "D-HATCH")
(entmake (list '(0 . "LINE") (cons 8 "D-HATCH") (cons 10 '(8109.700000 165.750000 0.000000)) (cons 11 '(8109.950000 165.500000 0.000000))))
(klay "D-HATCH")
(entmake (list '(0 . "LINE") (cons 8 "D-HATCH") (cons 10 '(8110.700000 165.750000 0.000000)) (cons 11 '(8110.950000 165.500000 0.000000))))
(klay "D-HATCH")
(entmake (list '(0 . "LINE") (cons 8 "D-HATCH") (cons 10 '(8111.700000 165.750000 0.000000)) (cons 11 '(8111.950000 165.500000 0.000000))))
(klay "D-HATCH")
(entmake (list '(0 . "LINE") (cons 8 "D-HATCH") (cons 10 '(8112.700000 165.750000 0.000000)) (cons 11 '(8112.950000 165.500000 0.000000))))
(klay "D-HATCH")
(entmake (list '(0 . "LINE") (cons 8 "D-HATCH") (cons 10 '(8113.700000 165.750000 0.000000)) (cons 11 '(8113.950000 165.500000 0.000000))))
(klay "D-HATCH")
(entmake (list '(0 . "LINE") (cons 8 "D-HATCH") (cons 10 '(8114.700000 165.750000 0.000000)) (cons 11 '(8114.950000 165.500000 0.000000))))
(klay "D-HATCH")
(entmake (list '(0 . "LINE") (cons 8 "D-HATCH") (cons 10 '(8115.700000 165.750000 0.000000)) (cons 11 '(8115.950000 165.500000 0.000000))))
(klay "D-HATCH")
(entmake (list '(0 . "LINE") (cons 8 "D-HATCH") (cons 10 '(8116.700000 165.750000 0.000000)) (cons 11 '(8116.950000 165.500000 0.000000))))
(klay "D-HATCH")
(entmake (list '(0 . "LINE") (cons 8 "D-HATCH") (cons 10 '(8117.700000 165.750000 0.000000)) (cons 11 '(8117.950000 165.500000 0.000000))))
(klay "D-FINE")
(command "_.RECTANG" '(8102.000000 157.500000 0.000000) '(8106.900000 163.100000 0.000000))
(klay "D-FINE")
(command "_.RECTANG" '(8109.850000 157.800000 0.000000) '(8112.150000 163.100000 0.000000))
(klay "D-FINE")
(command "_.RECTANG" '(8114.350000 157.800000 0.000000) '(8116.650000 163.100000 0.000000))
(klay "D-OUTLINE")
(command "_.RECTANG" '(8101.200000 162.750000 0.000000) '(8101.900000 163.100000 0.000000))
(klay "D-HATCH")
(entmake (list '(0 . "LINE") (cons 8 "D-HATCH") (cons 10 '(8101.850000 163.100000 0.000000)) (cons 11 '(8101.900000 163.050000 0.000000))))
(klay "D-OUTLINE")
(command "_.RECTANG" '(8107.000000 162.750000 0.000000) '(8109.830000 163.100000 0.000000))
(klay "D-HATCH")
(entmake (list '(0 . "LINE") (cons 8 "D-HATCH") (cons 10 '(8107.650000 163.100000 0.000000)) (cons 11 '(8108.000000 162.750000 0.000000))))
(klay "D-HATCH")
(entmake (list '(0 . "LINE") (cons 8 "D-HATCH") (cons 10 '(8108.650000 163.100000 0.000000)) (cons 11 '(8109.000000 162.750000 0.000000))))
(klay "D-HATCH")
(entmake (list '(0 . "LINE") (cons 8 "D-HATCH") (cons 10 '(8109.650000 163.100000 0.000000)) (cons 11 '(8109.830000 162.920000 0.000000))))
(klay "D-OUTLINE")
(command "_.RECTANG" '(8112.170000 162.750000 0.000000) '(8114.330000 163.100000 0.000000))
(klay "D-HATCH")
(entmake (list '(0 . "LINE") (cons 8 "D-HATCH") (cons 10 '(8112.820000 163.100000 0.000000)) (cons 11 '(8113.170000 162.750000 0.000000))))
(klay "D-HATCH")
(entmake (list '(0 . "LINE") (cons 8 "D-HATCH") (cons 10 '(8113.820000 163.100000 0.000000)) (cons 11 '(8114.170000 162.750000 0.000000))))
(klay "D-OUTLINE")
(command "_.RECTANG" '(8116.670000 162.750000 0.000000) '(8118.000000 163.100000 0.000000))
(klay "D-HATCH")
(entmake (list '(0 . "LINE") (cons 8 "D-HATCH") (cons 10 '(8117.320000 163.100000 0.000000)) (cons 11 '(8117.670000 162.750000 0.000000))))
(klay "D-OUTLINE")
(command "_.RECTANG" '(8102.000000 157.250000 0.000000) '(8102.250000 157.500000 0.000000))
(klay "D-OUTLINE")
(command "_.RECTANG" '(8106.650000 157.250000 0.000000) '(8106.900000 157.500000 0.000000))
(klay "D-TEXT")
(entmake (list '(0 . "TEXT") (cons 8 "D-TEXT") (cons 10 '(8095.000000 127.000000 0.000000)) (cons 40 1.05) (cons 1 "SECTION / STUDY") '(7 . "KITCHEN") '(50 . 0.0)))
(klay "D-TEXT")
(entmake (list '(0 . "TEXT") (cons 8 "D-TEXT") (cons 10 '(8095.000000 123.000000 0.000000)) (cons 40 1.05) (cons 1 "Runners by supplier") '(7 . "KITCHEN") '(50 . 0.0)))
(klay "D-OUTLINE")
(command "_.RECTANG" '(8127.000000 135.000000 0.000000) '(8142.000000 169.500000 0.000000))
(klay "D-OUTLINE")
(command "_.RECTANG" '(8127.000000 139.000000 0.000000) '(8142.000000 169.500000 0.000000))
(klay "D-OUTLINE")
(command "_.RECTANG" '(8131.823000 167.962200 0.000000) '(8137.177000 168.237800 0.000000))
(klay "D-DIMS")
(command "_.DIMLINEAR" '(8127.000000 169.500000 0.000000) '(8142.000000 169.500000 0.000000) "_H" '(8134.500000 177.000000 0.000000))
(klay "D-TITLE")
(entmake (list '(0 . "TEXT") (cons 8 "D-TITLE") (cons 10 '(8123.000000 127.000000 0.000000)) (cons 40 1.15) (cons 1 "GARBAGE + RECYCLING") '(7 . "KITCHEN") '(50 . 0.0)))
(klay "D-TEXT")
(entmake (list '(0 . "TEXT") (cons 8 "D-TEXT") (cons 10 '(8123.000000 123.000000 0.000000)) (cons 40 1.1) (cons 1 "FULL-HEIGHT PULLOUT") '(7 . "KITCHEN") '(50 . 0.0)))
(klay "D-OUTLINE")
(command "_.RECTANG" '(8147.000000 135.000000 0.000000) '(8171.250000 169.500000 0.000000))
(klay "D-OUTLINE")
(command "_.RECTANG" '(8170.500000 139.000000 0.000000) '(8171.250000 169.500000 0.000000))
(klay "D-HATCH")
(entmake (list '(0 . "LINE") (cons 8 "D-HATCH") (cons 10 '(8170.500000 140.000000 0.000000)) (cons 11 '(8171.250000 139.250000 0.000000))))
(klay "D-HATCH")
(entmake (list '(0 . "LINE") (cons 8 "D-HATCH") (cons 10 '(8170.500000 141.000000 0.000000)) (cons 11 '(8171.250000 140.250000 0.000000))))
(klay "D-HATCH")
(entmake (list '(0 . "LINE") (cons 8 "D-HATCH") (cons 10 '(8170.500000 142.000000 0.000000)) (cons 11 '(8171.250000 141.250000 0.000000))))
(klay "D-HATCH")
(entmake (list '(0 . "LINE") (cons 8 "D-HATCH") (cons 10 '(8170.500000 143.000000 0.000000)) (cons 11 '(8171.250000 142.250000 0.000000))))
(klay "D-HATCH")
(entmake (list '(0 . "LINE") (cons 8 "D-HATCH") (cons 10 '(8170.500000 144.000000 0.000000)) (cons 11 '(8171.250000 143.250000 0.000000))))
(klay "D-HATCH")
(entmake (list '(0 . "LINE") (cons 8 "D-HATCH") (cons 10 '(8170.500000 145.000000 0.000000)) (cons 11 '(8171.250000 144.250000 0.000000))))
(klay "D-HATCH")
(entmake (list '(0 . "LINE") (cons 8 "D-HATCH") (cons 10 '(8170.500000 146.000000 0.000000)) (cons 11 '(8171.250000 145.250000 0.000000))))
(klay "D-HATCH")
(entmake (list '(0 . "LINE") (cons 8 "D-HATCH") (cons 10 '(8170.500000 147.000000 0.000000)) (cons 11 '(8171.250000 146.250000 0.000000))))
(klay "D-HATCH")
(entmake (list '(0 . "LINE") (cons 8 "D-HATCH") (cons 10 '(8170.500000 148.000000 0.000000)) (cons 11 '(8171.250000 147.250000 0.000000))))
(klay "D-HATCH")
(entmake (list '(0 . "LINE") (cons 8 "D-HATCH") (cons 10 '(8170.500000 149.000000 0.000000)) (cons 11 '(8171.250000 148.250000 0.000000))))
(klay "D-HATCH")
(entmake (list '(0 . "LINE") (cons 8 "D-HATCH") (cons 10 '(8170.500000 150.000000 0.000000)) (cons 11 '(8171.250000 149.250000 0.000000))))
(klay "D-HATCH")
(entmake (list '(0 . "LINE") (cons 8 "D-HATCH") (cons 10 '(8170.500000 151.000000 0.000000)) (cons 11 '(8171.250000 150.250000 0.000000))))
(klay "D-HATCH")
(entmake (list '(0 . "LINE") (cons 8 "D-HATCH") (cons 10 '(8170.500000 152.000000 0.000000)) (cons 11 '(8171.250000 151.250000 0.000000))))
(klay "D-HATCH")
(entmake (list '(0 . "LINE") (cons 8 "D-HATCH") (cons 10 '(8170.500000 153.000000 0.000000)) (cons 11 '(8171.250000 152.250000 0.000000))))
(klay "D-HATCH")
(entmake (list '(0 . "LINE") (cons 8 "D-HATCH") (cons 10 '(8170.500000 154.000000 0.000000)) (cons 11 '(8171.250000 153.250000 0.000000))))
(klay "D-HATCH")
(entmake (list '(0 . "LINE") (cons 8 "D-HATCH") (cons 10 '(8170.500000 155.000000 0.000000)) (cons 11 '(8171.250000 154.250000 0.000000))))
(klay "D-HATCH")
(entmake (list '(0 . "LINE") (cons 8 "D-HATCH") (cons 10 '(8170.500000 156.000000 0.000000)) (cons 11 '(8171.250000 155.250000 0.000000))))
(klay "D-HATCH")
(entmake (list '(0 . "LINE") (cons 8 "D-HATCH") (cons 10 '(8170.500000 157.000000 0.000000)) (cons 11 '(8171.250000 156.250000 0.000000))))
(klay "D-HATCH")
(entmake (list '(0 . "LINE") (cons 8 "D-HATCH") (cons 10 '(8170.500000 158.000000 0.000000)) (cons 11 '(8171.250000 157.250000 0.000000))))
(klay "D-HATCH")
(entmake (list '(0 . "LINE") (cons 8 "D-HATCH") (cons 10 '(8170.500000 159.000000 0.000000)) (cons 11 '(8171.250000 158.250000 0.000000))))
(klay "D-HATCH")
(entmake (list '(0 . "LINE") (cons 8 "D-HATCH") (cons 10 '(8170.500000 160.000000 0.000000)) (cons 11 '(8171.250000 159.250000 0.000000))))
(klay "D-HATCH")
(entmake (list '(0 . "LINE") (cons 8 "D-HATCH") (cons 10 '(8170.500000 161.000000 0.000000)) (cons 11 '(8171.250000 160.250000 0.000000))))
(klay "D-HATCH")
(entmake (list '(0 . "LINE") (cons 8 "D-HATCH") (cons 10 '(8170.500000 162.000000 0.000000)) (cons 11 '(8171.250000 161.250000 0.000000))))
(klay "D-HATCH")
(entmake (list '(0 . "LINE") (cons 8 "D-HATCH") (cons 10 '(8170.500000 163.000000 0.000000)) (cons 11 '(8171.250000 162.250000 0.000000))))
(klay "D-HATCH")
(entmake (list '(0 . "LINE") (cons 8 "D-HATCH") (cons 10 '(8170.500000 164.000000 0.000000)) (cons 11 '(8171.250000 163.250000 0.000000))))
(klay "D-HATCH")
(entmake (list '(0 . "LINE") (cons 8 "D-HATCH") (cons 10 '(8170.500000 165.000000 0.000000)) (cons 11 '(8171.250000 164.250000 0.000000))))
(klay "D-HATCH")
(entmake (list '(0 . "LINE") (cons 8 "D-HATCH") (cons 10 '(8170.500000 166.000000 0.000000)) (cons 11 '(8171.250000 165.250000 0.000000))))
(klay "D-HATCH")
(entmake (list '(0 . "LINE") (cons 8 "D-HATCH") (cons 10 '(8170.500000 167.000000 0.000000)) (cons 11 '(8171.250000 166.250000 0.000000))))
(klay "D-HATCH")
(entmake (list '(0 . "LINE") (cons 8 "D-HATCH") (cons 10 '(8170.500000 168.000000 0.000000)) (cons 11 '(8171.250000 167.250000 0.000000))))
(klay "D-HATCH")
(entmake (list '(0 . "LINE") (cons 8 "D-HATCH") (cons 10 '(8170.500000 169.000000 0.000000)) (cons 11 '(8171.250000 168.250000 0.000000))))
(klay "D-HATCH")
(entmake (list '(0 . "LINE") (cons 8 "D-HATCH") (cons 10 '(8171.000000 169.500000 0.000000)) (cons 11 '(8171.250000 169.250000 0.000000))))
(klay "D-OUTLINE")
(command "_.RECTANG" '(8151.339000 141.290000 0.000000) '(8170.370000 141.790000 0.000000))
(klay "D-HATCH")
(entmake (list '(0 . "LINE") (cons 8 "D-HATCH") (cons 10 '(8151.839000 141.790000 0.000000)) (cons 11 '(8152.339000 141.290000 0.000000))))
(klay "D-HATCH")
(entmake (list '(0 . "LINE") (cons 8 "D-HATCH") (cons 10 '(8152.839000 141.790000 0.000000)) (cons 11 '(8153.339000 141.290000 0.000000))))
(klay "D-HATCH")
(entmake (list '(0 . "LINE") (cons 8 "D-HATCH") (cons 10 '(8153.839000 141.790000 0.000000)) (cons 11 '(8154.339000 141.290000 0.000000))))
(klay "D-HATCH")
(entmake (list '(0 . "LINE") (cons 8 "D-HATCH") (cons 10 '(8154.839000 141.790000 0.000000)) (cons 11 '(8155.339000 141.290000 0.000000))))
(klay "D-HATCH")
(entmake (list '(0 . "LINE") (cons 8 "D-HATCH") (cons 10 '(8155.839000 141.790000 0.000000)) (cons 11 '(8156.339000 141.290000 0.000000))))
(klay "D-HATCH")
(entmake (list '(0 . "LINE") (cons 8 "D-HATCH") (cons 10 '(8156.839000 141.790000 0.000000)) (cons 11 '(8157.339000 141.290000 0.000000))))
(klay "D-HATCH")
(entmake (list '(0 . "LINE") (cons 8 "D-HATCH") (cons 10 '(8157.839000 141.790000 0.000000)) (cons 11 '(8158.339000 141.290000 0.000000))))
(klay "D-HATCH")
(entmake (list '(0 . "LINE") (cons 8 "D-HATCH") (cons 10 '(8158.839000 141.790000 0.000000)) (cons 11 '(8159.339000 141.290000 0.000000))))
(klay "D-HATCH")
(entmake (list '(0 . "LINE") (cons 8 "D-HATCH") (cons 10 '(8159.839000 141.790000 0.000000)) (cons 11 '(8160.339000 141.290000 0.000000))))
(klay "D-HATCH")
(entmake (list '(0 . "LINE") (cons 8 "D-HATCH") (cons 10 '(8160.839000 141.790000 0.000000)) (cons 11 '(8161.339000 141.290000 0.000000))))
(klay "D-HATCH")
(entmake (list '(0 . "LINE") (cons 8 "D-HATCH") (cons 10 '(8161.839000 141.790000 0.000000)) (cons 11 '(8162.339000 141.290000 0.000000))))
(klay "D-HATCH")
(entmake (list '(0 . "LINE") (cons 8 "D-HATCH") (cons 10 '(8162.839000 141.790000 0.000000)) (cons 11 '(8163.339000 141.290000 0.000000))))
(klay "D-HATCH")
(entmake (list '(0 . "LINE") (cons 8 "D-HATCH") (cons 10 '(8163.839000 141.790000 0.000000)) (cons 11 '(8164.339000 141.290000 0.000000))))
(klay "D-HATCH")
(entmake (list '(0 . "LINE") (cons 8 "D-HATCH") (cons 10 '(8164.839000 141.790000 0.000000)) (cons 11 '(8165.339000 141.290000 0.000000))))
(klay "D-HATCH")
(entmake (list '(0 . "LINE") (cons 8 "D-HATCH") (cons 10 '(8165.839000 141.790000 0.000000)) (cons 11 '(8166.339000 141.290000 0.000000))))
(klay "D-HATCH")
(entmake (list '(0 . "LINE") (cons 8 "D-HATCH") (cons 10 '(8166.839000 141.790000 0.000000)) (cons 11 '(8167.339000 141.290000 0.000000))))
(klay "D-HATCH")
(entmake (list '(0 . "LINE") (cons 8 "D-HATCH") (cons 10 '(8167.839000 141.790000 0.000000)) (cons 11 '(8168.339000 141.290000 0.000000))))
(klay "D-HATCH")
(entmake (list '(0 . "LINE") (cons 8 "D-HATCH") (cons 10 '(8168.839000 141.790000 0.000000)) (cons 11 '(8169.339000 141.290000 0.000000))))
(klay "D-HATCH")
(entmake (list '(0 . "LINE") (cons 8 "D-HATCH") (cons 10 '(8169.839000 141.790000 0.000000)) (cons 11 '(8170.339000 141.290000 0.000000))))
(klay "D-OUTLINE")
(command "_.RECTANG" '(8151.209000 141.790000 0.000000) '(8151.709000 144.500000 0.000000))
(klay "D-HATCH")
(entmake (list '(0 . "LINE") (cons 8 "D-HATCH") (cons 10 '(8151.209000 142.790000 0.000000)) (cons 11 '(8151.709000 142.290000 0.000000))))
(klay "D-HATCH")
(entmake (list '(0 . "LINE") (cons 8 "D-HATCH") (cons 10 '(8151.209000 143.790000 0.000000)) (cons 11 '(8151.709000 143.290000 0.000000))))
(klay "D-HATCH")
(entmake (list '(0 . "LINE") (cons 8 "D-HATCH") (cons 10 '(8151.499000 144.500000 0.000000)) (cons 11 '(8151.709000 144.290000 0.000000))))
(klay "D-OUTLINE")
(command "_.RECTANG" '(8170.000000 141.790000 0.000000) '(8170.500000 168.500000 0.000000))
(klay "D-HATCH")
(entmake (list '(0 . "LINE") (cons 8 "D-HATCH") (cons 10 '(8170.000000 142.790000 0.000000)) (cons 11 '(8170.500000 142.290000 0.000000))))
(klay "D-HATCH")
(entmake (list '(0 . "LINE") (cons 8 "D-HATCH") (cons 10 '(8170.000000 143.790000 0.000000)) (cons 11 '(8170.500000 143.290000 0.000000))))
(klay "D-HATCH")
(entmake (list '(0 . "LINE") (cons 8 "D-HATCH") (cons 10 '(8170.000000 144.790000 0.000000)) (cons 11 '(8170.500000 144.290000 0.000000))))
(klay "D-HATCH")
(entmake (list '(0 . "LINE") (cons 8 "D-HATCH") (cons 10 '(8170.000000 145.790000 0.000000)) (cons 11 '(8170.500000 145.290000 0.000000))))
(klay "D-HATCH")
(entmake (list '(0 . "LINE") (cons 8 "D-HATCH") (cons 10 '(8170.000000 146.790000 0.000000)) (cons 11 '(8170.500000 146.290000 0.000000))))
(klay "D-HATCH")
(entmake (list '(0 . "LINE") (cons 8 "D-HATCH") (cons 10 '(8170.000000 147.790000 0.000000)) (cons 11 '(8170.500000 147.290000 0.000000))))
(klay "D-HATCH")
(entmake (list '(0 . "LINE") (cons 8 "D-HATCH") (cons 10 '(8170.000000 148.790000 0.000000)) (cons 11 '(8170.500000 148.290000 0.000000))))
(klay "D-HATCH")
(entmake (list '(0 . "LINE") (cons 8 "D-HATCH") (cons 10 '(8170.000000 149.790000 0.000000)) (cons 11 '(8170.500000 149.290000 0.000000))))
(klay "D-HATCH")
(entmake (list '(0 . "LINE") (cons 8 "D-HATCH") (cons 10 '(8170.000000 150.790000 0.000000)) (cons 11 '(8170.500000 150.290000 0.000000))))
(klay "D-HATCH")
(entmake (list '(0 . "LINE") (cons 8 "D-HATCH") (cons 10 '(8170.000000 151.790000 0.000000)) (cons 11 '(8170.500000 151.290000 0.000000))))
(klay "D-HATCH")
(entmake (list '(0 . "LINE") (cons 8 "D-HATCH") (cons 10 '(8170.000000 152.790000 0.000000)) (cons 11 '(8170.500000 152.290000 0.000000))))
(klay "D-HATCH")
(entmake (list '(0 . "LINE") (cons 8 "D-HATCH") (cons 10 '(8170.000000 153.790000 0.000000)) (cons 11 '(8170.500000 153.290000 0.000000))))
(klay "D-HATCH")
(entmake (list '(0 . "LINE") (cons 8 "D-HATCH") (cons 10 '(8170.000000 154.790000 0.000000)) (cons 11 '(8170.500000 154.290000 0.000000))))
(klay "D-HATCH")
(entmake (list '(0 . "LINE") (cons 8 "D-HATCH") (cons 10 '(8170.000000 155.790000 0.000000)) (cons 11 '(8170.500000 155.290000 0.000000))))
(klay "D-HATCH")
(entmake (list '(0 . "LINE") (cons 8 "D-HATCH") (cons 10 '(8170.000000 156.790000 0.000000)) (cons 11 '(8170.500000 156.290000 0.000000))))
(klay "D-HATCH")
(entmake (list '(0 . "LINE") (cons 8 "D-HATCH") (cons 10 '(8170.000000 157.790000 0.000000)) (cons 11 '(8170.500000 157.290000 0.000000))))
(klay "D-HATCH")
(entmake (list '(0 . "LINE") (cons 8 "D-HATCH") (cons 10 '(8170.000000 158.790000 0.000000)) (cons 11 '(8170.500000 158.290000 0.000000))))
(klay "D-HATCH")
(entmake (list '(0 . "LINE") (cons 8 "D-HATCH") (cons 10 '(8170.000000 159.790000 0.000000)) (cons 11 '(8170.500000 159.290000 0.000000))))
(klay "D-HATCH")
(entmake (list '(0 . "LINE") (cons 8 "D-HATCH") (cons 10 '(8170.000000 160.790000 0.000000)) (cons 11 '(8170.500000 160.290000 0.000000))))
(klay "D-HATCH")
(entmake (list '(0 . "LINE") (cons 8 "D-HATCH") (cons 10 '(8170.000000 161.790000 0.000000)) (cons 11 '(8170.500000 161.290000 0.000000))))
(klay "D-HATCH")
(entmake (list '(0 . "LINE") (cons 8 "D-HATCH") (cons 10 '(8170.000000 162.790000 0.000000)) (cons 11 '(8170.500000 162.290000 0.000000))))
(klay "D-HATCH")
(entmake (list '(0 . "LINE") (cons 8 "D-HATCH") (cons 10 '(8170.000000 163.790000 0.000000)) (cons 11 '(8170.500000 163.290000 0.000000))))
(klay "D-HATCH")
(entmake (list '(0 . "LINE") (cons 8 "D-HATCH") (cons 10 '(8170.000000 164.790000 0.000000)) (cons 11 '(8170.500000 164.290000 0.000000))))
(klay "D-HATCH")
(entmake (list '(0 . "LINE") (cons 8 "D-HATCH") (cons 10 '(8170.000000 165.790000 0.000000)) (cons 11 '(8170.500000 165.290000 0.000000))))
(klay "D-HATCH")
(entmake (list '(0 . "LINE") (cons 8 "D-HATCH") (cons 10 '(8170.000000 166.790000 0.000000)) (cons 11 '(8170.500000 166.290000 0.000000))))
(klay "D-HATCH")
(entmake (list '(0 . "LINE") (cons 8 "D-HATCH") (cons 10 '(8170.000000 167.790000 0.000000)) (cons 11 '(8170.500000 167.290000 0.000000))))
(klay "D-HATCH")
(entmake (list '(0 . "LINE") (cons 8 "D-HATCH") (cons 10 '(8170.290000 168.500000 0.000000)) (cons 11 '(8170.500000 168.290000 0.000000))))
(klay "D-FINE")
(entmake (list '(0 . "LINE") (cons 8 "D-FINE") (cons 10 '(8150.815000 140.790000 0.000000)) (cons 11 '(8170.500000 140.790000 0.000000))))
(klay "D-FINE")
(command "_.RECTANG" '(8154.000000 141.790000 0.000000) '(8161.500000 160.290000 0.000000))
(klay "D-FINE")
(command "_.RECTANG" '(8153.960000 160.150000 0.000000) '(8161.540000 160.450000 0.000000))
(klay "D-FINE")
(command "_.RECTANG" '(8162.000000 141.790000 0.000000) '(8169.500000 160.290000 0.000000))
(klay "D-FINE")
(command "_.RECTANG" '(8161.960000 160.150000 0.000000) '(8169.540000 160.450000 0.000000))
(klay "D-OUTLINE")
(command "_.RECTANG" '(8161.630000 141.790000 0.000000) '(8161.870000 160.150000 0.000000))
(klay "D-HATCH")
(entmake (list '(0 . "LINE") (cons 8 "D-HATCH") (cons 10 '(8161.630000 142.790000 0.000000)) (cons 11 '(8161.870000 142.550000 0.000000))))
(klay "D-HATCH")
(entmake (list '(0 . "LINE") (cons 8 "D-HATCH") (cons 10 '(8161.630000 143.790000 0.000000)) (cons 11 '(8161.870000 143.550000 0.000000))))
(klay "D-HATCH")
(entmake (list '(0 . "LINE") (cons 8 "D-HATCH") (cons 10 '(8161.630000 144.790000 0.000000)) (cons 11 '(8161.870000 144.550000 0.000000))))
(klay "D-HATCH")
(entmake (list '(0 . "LINE") (cons 8 "D-HATCH") (cons 10 '(8161.630000 145.790000 0.000000)) (cons 11 '(8161.870000 145.550000 0.000000))))
(klay "D-HATCH")
(entmake (list '(0 . "LINE") (cons 8 "D-HATCH") (cons 10 '(8161.630000 146.790000 0.000000)) (cons 11 '(8161.870000 146.550000 0.000000))))
(klay "D-HATCH")
(entmake (list '(0 . "LINE") (cons 8 "D-HATCH") (cons 10 '(8161.630000 147.790000 0.000000)) (cons 11 '(8161.870000 147.550000 0.000000))))
(klay "D-HATCH")
(entmake (list '(0 . "LINE") (cons 8 "D-HATCH") (cons 10 '(8161.630000 148.790000 0.000000)) (cons 11 '(8161.870000 148.550000 0.000000))))
(klay "D-HATCH")
(entmake (list '(0 . "LINE") (cons 8 "D-HATCH") (cons 10 '(8161.630000 149.790000 0.000000)) (cons 11 '(8161.870000 149.550000 0.000000))))
(klay "D-HATCH")
(entmake (list '(0 . "LINE") (cons 8 "D-HATCH") (cons 10 '(8161.630000 150.790000 0.000000)) (cons 11 '(8161.870000 150.550000 0.000000))))
(klay "D-HATCH")
(entmake (list '(0 . "LINE") (cons 8 "D-HATCH") (cons 10 '(8161.630000 151.790000 0.000000)) (cons 11 '(8161.870000 151.550000 0.000000))))
(klay "D-HATCH")
(entmake (list '(0 . "LINE") (cons 8 "D-HATCH") (cons 10 '(8161.630000 152.790000 0.000000)) (cons 11 '(8161.870000 152.550000 0.000000))))
(klay "D-HATCH")
(entmake (list '(0 . "LINE") (cons 8 "D-HATCH") (cons 10 '(8161.630000 153.790000 0.000000)) (cons 11 '(8161.870000 153.550000 0.000000))))
(klay "D-HATCH")
(entmake (list '(0 . "LINE") (cons 8 "D-HATCH") (cons 10 '(8161.630000 154.790000 0.000000)) (cons 11 '(8161.870000 154.550000 0.000000))))
(klay "D-HATCH")
(entmake (list '(0 . "LINE") (cons 8 "D-HATCH") (cons 10 '(8161.630000 155.790000 0.000000)) (cons 11 '(8161.870000 155.550000 0.000000))))
(klay "D-HATCH")
(entmake (list '(0 . "LINE") (cons 8 "D-HATCH") (cons 10 '(8161.630000 156.790000 0.000000)) (cons 11 '(8161.870000 156.550000 0.000000))))
(klay "D-HATCH")
(entmake (list '(0 . "LINE") (cons 8 "D-HATCH") (cons 10 '(8161.630000 157.790000 0.000000)) (cons 11 '(8161.870000 157.550000 0.000000))))
(klay "D-HATCH")
(entmake (list '(0 . "LINE") (cons 8 "D-HATCH") (cons 10 '(8161.630000 158.790000 0.000000)) (cons 11 '(8161.870000 158.550000 0.000000))))
(klay "D-HATCH")
(entmake (list '(0 . "LINE") (cons 8 "D-HATCH") (cons 10 '(8161.630000 159.790000 0.000000)) (cons 11 '(8161.870000 159.550000 0.000000))))
(klay "D-TEXT")
(entmake (list '(0 . "TEXT") (cons 8 "D-TEXT") (cons 10 '(8146.000000 127.000000 0.000000)) (cons 40 1.05) (cons 1 "SECTION / STUDY") '(7 . "KITCHEN") '(50 . 0.0)))
(klay "D-TEXT")
(entmake (list '(0 . "TEXT") (cons 8 "D-TEXT") (cons 10 '(8146.000000 123.000000 0.000000)) (cons 40 1.05) (cons 1 "Runners by supplier") '(7 . "KITCHEN") '(50 . 0.0)))
(klay "D-OUTLINE")
(command "_.RECTANG" '(8025.000000 32.000000 0.000000) '(8061.000000 112.000000 0.000000))
(klay "D-OUTLINE")
(command "_.RECTANG" '(8027.600000 66.800000 0.000000) '(8028.900000 70.200000 0.000000))
(klay "D-OUTLINE")
(command "_.RECTANG" '(8029.000000 37.000000 0.000000) '(8057.000000 56.000000 0.000000))
(klay "D-OUTLINE")
(command "_.RECTANG" '(8029.000000 60.000000 0.000000) '(8057.000000 80.000000 0.000000))
(klay "D-OUTLINE")
(command "_.RECTANG" '(8029.000000 84.000000 0.000000) '(8057.000000 107.000000 0.000000))
(klay "D-DIMS")
(command "_.DIMLINEAR" '(8025.000000 112.000000 0.000000) '(8061.000000 112.000000 0.000000) "_H" '(8043.000000 118.000000 0.000000))
(klay "D-DIMS")
(command "_.DIMLINEAR" '(8025.000000 32.000000 0.000000) '(8025.000000 112.000000 0.000000) "_V" '(8018.000000 72.000000 0.000000))
(klay "D-TITLE")
(entmake (list '(0 . "TEXT") (cons 8 "D-TITLE") (cons 10 '(8025.000000 29.000000 0.000000)) (cons 40 1.45) (cons 1 "16  POCKET DOOR / INSIDE") '(7 . "KITCHEN") '(50 . 0.0)))
(klay "D-OUTLINE")
(command "_.RECTANG" '(8091.000000 70.000000 0.000000) '(8098.250000 74.000000 0.000000))
(klay "D-OUTLINE")
(command "_.RECTANG" '(8098.250000 70.000000 0.000000) '(8134.250000 70.600000 0.000000))
(klay "D-OUTLINE")
(command "_.RECTANG" '(8098.250000 73.400000 0.000000) '(8134.250000 74.000000 0.000000))
(klay "D-OUTLINE")
(command "_.RECTANG" '(8134.250000 70.875000 0.000000) '(8170.250000 72.625000 0.000000))
(klay "D-OUTLINE")
(command "_.RECTANG" '(8170.250000 70.000000 0.000000) '(8184.250000 74.000000 0.000000))
(klay "D-OUTLINE")
(command "_.RECTANG" '(8166.350000 72.650000 0.000000) '(8167.650000 72.800000 0.000000))
(klay "D-OUTLINE")
(entmake (list '(0 . "LINE") (cons 8 "D-OUTLINE") (cons 10 '(8166.000000 81.000000 0.000000)) (cons 11 '(8109.000000 81.000000 0.000000))))
(klay "D-FINE")
(entmake (list '(0 . "LINE") (cons 8 "D-FINE") (cons 10 '(8109.000000 81.000000 0.000000)) (cons 11 '(8112.000000 82.500000 0.000000))))
(klay "D-FINE")
(entmake (list '(0 . "LINE") (cons 8 "D-FINE") (cons 10 '(8109.000000 81.000000 0.000000)) (cons 11 '(8112.000000 79.500000 0.000000))))
(klay "D-TEXT")
(entmake (list '(0 . "TEXT") (cons 8 "D-TEXT") (cons 10 '(8102.000000 86.000000 0.000000)) (cons 40 1.2) (cons 1 "SLIDE TOWARD CABINETS") '(7 . "KITCHEN") '(50 . 0.0)))
(klay "D-DIMS")
(command "_.DIMLINEAR" '(8091.000000 70.000000 0.000000) '(8098.250000 70.000000 0.000000) "_H" '(8094.625000 64.000000 0.000000))
(klay "D-DIMS")
(command "_.DIMLINEAR" '(8098.250000 70.000000 0.000000) '(8134.250000 70.000000 0.000000) "_H" '(8116.250000 58.000000 0.000000))
(klay "D-DIMS")
(command "_.DIMLINEAR" '(8134.250000 70.000000 0.000000) '(8170.250000 70.000000 0.000000) "_H" '(8152.250000 64.000000 0.000000))
(klay "D-TEXT")
(entmake (list '(0 . "TEXT") (cons 8 "D-TEXT") (cons 10 '(8091.000000 42.000000 0.000000)) (cons 40 1.26) (cons 1 "Pocket D120.25-156.25; opening D156.25-192.25.") '(7 . "KITCHEN") '(50 . 0.0)))
(klay "D-TEXT")
(entmake (list '(0 . "TEXT") (cons 8 "D-TEXT") (cons 10 '(8091.000000 39.720000 0.000000)) (cons 40 1.26) (cons 1 "7.25 from cabinet end D113 to pocket start.") '(7 . "KITCHEN") '(50 . 0.0)))
(klay "D-TEXT")
(entmake (list '(0 . "TEXT") (cons 8 "D-TEXT") (cons 10 '(8091.000000 37.440000 0.000000)) (cons 40 1.26) (cons 1 "Inside-left pull at D189; opening position retained.") '(7 . "KITCHEN") '(50 . 0.0)))
(klay "D-TEXT")
(entmake (list '(0 . "TEXT") (cons 8 "D-TEXT") (cons 10 '(8211.000000 183.000000 0.000000)) (cons 40 1.26) (cons 1 "22 OCTOBER COORDINATION") '(7 . "KITCHEN") '(50 . 0.0)))
(klay "D-TEXT")
(entmake (list '(0 . "TEXT") (cons 8 "D-TEXT") (cons 10 '(8211.000000 180.720000 0.000000)) (cons 40 1.26) (cons 1 "Range pullouts: 10 in. bays.") '(7 . "KITCHEN") '(50 . 0.0)))
(klay "D-TEXT")
(entmake (list '(0 . "TEXT") (cons 8 "D-TEXT") (cons 10 '(8211.000000 178.440000 0.000000)) (cons 40 1.26) (cons 1 "Spice left / utensils right facing range.") '(7 . "KITCHEN") '(50 . 0.0)))
(klay "D-TEXT")
(entmake (list '(0 . "TEXT") (cons 8 "D-TEXT") (cons 10 '(8211.000000 176.160000 0.000000)) (cons 40 1.26) (cons 1 "Full-height fronts with top horizontal pulls.") '(7 . "KITCHEN") '(50 . 0.0)))
(klay "D-TEXT")
(entmake (list '(0 . "TEXT") (cons 8 "D-TEXT") (cons 10 '(8211.000000 173.880000 0.000000)) (cons 40 1.26) (cons 1 "Waste bay remains 15 in. wide.") '(7 . "KITCHEN") '(50 . 0.0)))
(klay "D-TEXT")
(entmake (list '(0 . "TEXT") (cons 8 "D-TEXT") (cons 10 '(8211.000000 171.600000 0.000000)) (cons 40 1.26) (cons 1 "Two tandem bins + divider/support.") '(7 . "KITCHEN") '(50 . 0.0)))
(klay "D-TEXT")
(entmake (list '(0 . "TEXT") (cons 8 "D-TEXT") (cons 10 '(8211.000000 169.320000 0.000000)) (cons 40 1.26) (cons 1 "") '(7 . "KITCHEN") '(50 . 0.0)))
(klay "D-TEXT")
(entmake (list '(0 . "TEXT") (cons 8 "D-TEXT") (cons 10 '(8211.000000 167.040000 0.000000)) (cons 40 1.26) (cons 1 "INTERIORS ARE SCHEMATIC") '(7 . "KITCHEN") '(50 . 0.0)))
(klay "D-TEXT")
(entmake (list '(0 . "TEXT") (cons 8 "D-TEXT") (cons 10 '(8211.000000 164.760000 0.000000)) (cons 40 1.26) (cons 1 "Proposed fit coordinated with 3D study.") '(7 . "KITCHEN") '(50 . 0.0)))
(klay "D-TEXT")
(entmake (list '(0 . "TEXT") (cons 8 "D-TEXT") (cons 10 '(8211.000000 162.480000 0.000000)) (cons 40 1.26) (cons 1 "500 mm runner / final rating pending.") '(7 . "KITCHEN") '(50 . 0.0)))
(klay "D-TEXT")
(entmake (list '(0 . "TEXT") (cons 8 "D-TEXT") (cons 10 '(8211.000000 160.200000 0.000000)) (cons 40 1.26) (cons 1 "Bins: 10.9 W x 7.5 D x 18.5 H study.") '(7 . "KITCHEN") '(50 . 0.0)))
(klay "D-TEXT")
(entmake (list '(0 . "TEXT") (cons 8 "D-TEXT") (cons 10 '(8211.000000 157.920000 0.000000)) (cons 40 1.26) (cons 1 "Final capacities and supplier pending.") '(7 . "KITCHEN") '(50 . 0.0)))
(klay "D-TEXT")
(entmake (list '(0 . "TEXT") (cons 8 "D-TEXT") (cons 10 '(8211.000000 155.640000 0.000000)) (cons 40 1.26) (cons 1 "No fixed shelf / door hinges in pullouts.") '(7 . "KITCHEN") '(50 . 0.0)))
(klay "D-TEXT")
(entmake (list '(0 . "TEXT") (cons 8 "D-TEXT") (cons 10 '(8211.000000 153.360000 0.000000)) (cons 40 1.26) (cons 1 "Closed-front elevations on A201 / A202.") '(7 . "KITCHEN") '(50 . 0.0)))
(klay "D-TEXT")
(entmake (list '(0 . "TEXT") (cons 8 "D-TEXT") (cons 10 '(8211.000000 151.080000 0.000000)) (cons 40 1.26) (cons 1 "") '(7 . "KITCHEN") '(50 . 0.0)))
(klay "D-TEXT")
(entmake (list '(0 . "TEXT") (cons 8 "D-TEXT") (cons 10 '(8211.000000 148.800000 0.000000)) (cons 40 1.26) (cons 1 "POCKET DOOR") '(7 . "KITCHEN") '(50 . 0.0)))
(klay "D-TEXT")
(entmake (list '(0 . "TEXT") (cons 8 "D-TEXT") (cons 10 '(8211.000000 146.520000 0.000000)) (cons 40 1.26) (cons 1 "Handle left from inside kitchen.") '(7 . "KITCHEN") '(50 . 0.0)))
(klay "D-TEXT")
(entmake (list '(0 . "TEXT") (cons 8 "D-TEXT") (cons 10 '(8211.000000 144.240000 0.000000)) (cons 40 1.26) (cons 1 "Leaf slides right toward cabinet side.") '(7 . "KITCHEN") '(50 . 0.0)))
(klay "D-TEXT")
(entmake (list '(0 . "TEXT") (cons 8 "D-TEXT") (cons 10 '(8211.000000 141.960000 0.000000)) (cons 40 1.26) (cons 1 "36 x 80 opening position unchanged.") '(7 . "KITCHEN") '(50 . 0.0)))
(klay "D-TEXT")
(entmake (list '(0 . "TEXT") (cons 8 "D-TEXT") (cons 10 '(8211.000000 139.680000 0.000000)) (cons 40 1.26) (cons 1 "Pocket cavity between retained wall skins.") '(7 . "KITCHEN") '(50 . 0.0)))
(klay "D-TEXT")
(entmake (list '(0 . "TEXT") (cons 8 "D-TEXT") (cons 10 '(8211.000000 137.400000 0.000000)) (cons 40 1.26) (cons 1 "Kit, wall framing and services to verify.") '(7 . "KITCHEN") '(50 . 0.0)))
(klay "D-TEXT")
(entmake (list '(0 . "TEXT") (cons 8 "D-TEXT") (cons 10 '(8211.000000 135.120000 0.000000)) (cons 40 1.26) (cons 1 "") '(7 . "KITCHEN") '(50 . 0.0)))
(klay "D-TEXT")
(entmake (list '(0 . "TEXT") (cons 8 "D-TEXT") (cons 10 '(8211.000000 132.840000 0.000000)) (cons 40 1.26) (cons 1 "SOURCE") '(7 . "KITCHEN") '(50 . 0.0)))
(klay "D-TEXT")
(entmake (list '(0 . "TEXT") (cons 8 "D-TEXT") (cons 10 '(8211.000000 130.560000 0.000000)) (cons 40 1.26) (cons 1 "Owner coordination notes 22 October.") '(7 . "KITCHEN") '(50 . 0.0)))
(klay "D-TEXT")
(entmake (list '(0 . "TEXT") (cons 8 "D-TEXT") (cons 10 '(8211.000000 128.280000 0.000000)) (cons 40 1.26) (cons 1 "Cabinet pp. 5 / 6; plan A101.") '(7 . "KITCHEN") '(50 . 0.0)))
(if (member "A101" (layoutlist)) (command "_.-LAYOUT" "_D" "A101"))
(command "_.-LAYOUT" "_N" "A101")
(setvar "CTAB" "A101")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(192.000000 144.000000 0.000000) 288)
(command "_.PSPACE")
(command "_.MVIEW" "_LOCK" "_ON" "_ALL" "")
(if (member "A201" (layoutlist)) (command "_.-LAYOUT" "_D" "A201"))
(command "_.-LAYOUT" "_N" "A201")
(setvar "CTAB" "A201")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(1144.000000 108.000000 0.000000) 216)
(command "_.PSPACE")
(command "_.MVIEW" "_LOCK" "_ON" "_ALL" "")
(if (member "A202" (layoutlist)) (command "_.-LAYOUT" "_D" "A202"))
(command "_.-LAYOUT" "_N" "A202")
(setvar "CTAB" "A202")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(2144.000000 108.000000 0.000000) 216)
(command "_.PSPACE")
(command "_.MVIEW" "_LOCK" "_ON" "_ALL" "")
(if (member "A203" (layoutlist)) (command "_.-LAYOUT" "_D" "A203"))
(command "_.-LAYOUT" "_N" "A203")
(setvar "CTAB" "A203")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(3144.000000 108.000000 0.000000) 216)
(command "_.PSPACE")
(command "_.MVIEW" "_LOCK" "_ON" "_ALL" "")
(if (member "A401" (layoutlist)) (command "_.-LAYOUT" "_D" "A401"))
(command "_.-LAYOUT" "_N" "A401")
(setvar "CTAB" "A401")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(4144.000000 108.000000 0.000000) 216)
(command "_.PSPACE")
(command "_.MVIEW" "_LOCK" "_ON" "_ALL" "")
(if (member "A501" (layoutlist)) (command "_.-LAYOUT" "_D" "A501"))
(command "_.-LAYOUT" "_N" "A501")
(setvar "CTAB" "A501")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(5024.000000 18.000000 0.000000) 36)
(command "_.PSPACE")
(command "_.MVIEW" "_LOCK" "_ON" "_ALL" "")
(if (member "A502" (layoutlist)) (command "_.-LAYOUT" "_D" "A502"))
(command "_.-LAYOUT" "_N" "A502")
(setvar "CTAB" "A502")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(6096.000000 72.000000 0.000000) 144)
(command "_.PSPACE")
(command "_.MVIEW" "_LOCK" "_ON" "_ALL" "")
(if (member "A602" (layoutlist)) (command "_.-LAYOUT" "_D" "A602"))
(command "_.-LAYOUT" "_N" "A602")
(setvar "CTAB" "A602")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(7144.000000 108.000000 0.000000) 216)
(command "_.PSPACE")
(command "_.MVIEW" "_LOCK" "_ON" "_ALL" "")
(if (member "A402" (layoutlist)) (command "_.-LAYOUT" "_D" "A402"))
(command "_.-LAYOUT" "_N" "A402")
(setvar "CTAB" "A402")
(command "_.PSPACE")
(if (setq oldvp (ssget "_X" (list '(0 . "VIEWPORT") (cons 410 (getvar "CTAB"))))) (command "_.ERASE" oldvp ""))
(klay "VPORT")
(command "_.MVIEW" '(0 0) '(24 18))
(command "_.MSPACE")
(command "_.UCS" "_W")
(command "_.PLAN" "_W")
(command "_.ZOOM" "_C" '(8144.000000 108.000000 0.000000) 216)
(command "_.PSPACE")
(command "_.MVIEW" "_LOCK" "_ON" "_ALL" "")
(setvar "CTAB" "A101")
(command "_.ZOOM" "_E")
(command "_.QSAVE")
(princ "\nKITCHEN_SHEETS_COMPLETE\n") (princ)

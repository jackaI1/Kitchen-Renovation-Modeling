(setvar "TILEMODE" 1)
(setvar "CMDECHO" 0)
(setvar "OSMODE" 0)
(setvar "DYNMODE" 0)
(setvar "INSUNITS" 1)
(setvar "MEASUREMENT" 0)
(setvar "LUNITS" 2)
(setvar "LUPREC" 4)
(setvar "FILEDIA" 0)
(setvar "GRIDMODE" 0)
(setvar "UCSICON" 0)
(command "_.UCS" "_W")
(command "_.PLAN" "_W")
(defun klay (n) (setvar "CLAYER" n))
(defun kbox (a b) (command "_.BOX" a (list (car b) (cadr b) (caddr a)) (- (caddr b) (caddr a))) (entlast))
(defun kname (e n) (entmod (append (entget e) (list (list -3 (list "KITCHEN" (cons 1000 n)))))))
(regapp "KITCHEN")
(if (not (tblsearch "LAYER" "F-CONTEXT")) (entmake (list '(0 . "LAYER") '(100 . "AcDbSymbolTableRecord") '(100 . "AcDbLayerTableRecord") (cons 2 "F-CONTEXT") '(70 . 0) (cons 62 8) '(6 . "Continuous") (cons 370 13))))
(if (not (tblsearch "LAYER" "A-WALL")) (entmake (list '(0 . "LAYER") '(100 . "AcDbSymbolTableRecord") '(100 . "AcDbLayerTableRecord") (cons 2 "A-WALL") '(70 . 0) (cons 62 8) '(6 . "Continuous") (cons 370 35))))
(if (not (tblsearch "LAYER" "A-FLOOR")) (entmake (list '(0 . "LAYER") '(100 . "AcDbSymbolTableRecord") '(100 . "AcDbLayerTableRecord") (cons 2 "A-FLOOR") '(70 . 0) (cons 62 8) '(6 . "Continuous") (cons 370 18))))
(if (not (tblsearch "LAYER" "A-CEILING")) (entmake (list '(0 . "LAYER") '(100 . "AcDbSymbolTableRecord") '(100 . "AcDbLayerTableRecord") (cons 2 "A-CEILING") '(70 . 0) (cons 62 8) '(6 . "Continuous") (cons 370 18))))
(if (not (tblsearch "LAYER" "A-JOINERY")) (entmake (list '(0 . "LAYER") '(100 . "AcDbSymbolTableRecord") '(100 . "AcDbLayerTableRecord") (cons 2 "A-JOINERY") '(70 . 0) (cons 62 7) '(6 . "Continuous") (cons 370 25))))
(if (not (tblsearch "LAYER" "A-GLASS")) (entmake (list '(0 . "LAYER") '(100 . "AcDbSymbolTableRecord") '(100 . "AcDbLayerTableRecord") (cons 2 "A-GLASS") '(70 . 0) (cons 62 4) '(6 . "Continuous") (cons 370 13))))
(if (not (tblsearch "LAYER" "C-CARCASS")) (entmake (list '(0 . "LAYER") '(100 . "AcDbSymbolTableRecord") '(100 . "AcDbLayerTableRecord") (cons 2 "C-CARCASS") '(70 . 0) (cons 62 32) '(6 . "Continuous") (cons 370 18))))
(if (not (tblsearch "LAYER" "C-FRONTS")) (entmake (list '(0 . "LAYER") '(100 . "AcDbSymbolTableRecord") '(100 . "AcDbLayerTableRecord") (cons 2 "C-FRONTS") '(70 . 0) (cons 62 33) '(6 . "Continuous") (cons 370 25))))
(if (not (tblsearch "LAYER" "C-PLINTH")) (entmake (list '(0 . "LAYER") '(100 . "AcDbSymbolTableRecord") '(100 . "AcDbLayerTableRecord") (cons 2 "C-PLINTH") '(70 . 0) (cons 62 8) '(6 . "Continuous") (cons 370 18))))
(if (not (tblsearch "LAYER" "C-HARDWARE")) (entmake (list '(0 . "LAYER") '(100 . "AcDbSymbolTableRecord") '(100 . "AcDbLayerTableRecord") (cons 2 "C-HARDWARE") '(70 . 0) (cons 62 9) '(6 . "Continuous") (cons 370 13))))
(if (not (tblsearch "LAYER" "C-GLASS")) (entmake (list '(0 . "LAYER") '(100 . "AcDbSymbolTableRecord") '(100 . "AcDbLayerTableRecord") (cons 2 "C-GLASS") '(70 . 0) (cons 62 4) '(6 . "Continuous") (cons 370 13))))
(if (not (tblsearch "LAYER" "S-PORCELAIN")) (entmake (list '(0 . "LAYER") '(100 . "AcDbSymbolTableRecord") '(100 . "AcDbLayerTableRecord") (cons 2 "S-PORCELAIN") '(70 . 0) (cons 62 7) '(6 . "Continuous") (cons 370 25))))
(if (not (tblsearch "LAYER" "M-METAL")) (entmake (list '(0 . "LAYER") '(100 . "AcDbSymbolTableRecord") '(100 . "AcDbLayerTableRecord") (cons 2 "M-METAL") '(70 . 0) (cons 62 9) '(6 . "Continuous") (cons 370 18))))
(if (not (tblsearch "LAYER" "M-GLASS")) (entmake (list '(0 . "LAYER") '(100 . "AcDbSymbolTableRecord") '(100 . "AcDbLayerTableRecord") (cons 2 "M-GLASS") '(70 . 0) (cons 62 250) '(6 . "Continuous") (cons 370 13))))
(if (not (tblsearch "LAYER" "M-DUCT")) (entmake (list '(0 . "LAYER") '(100 . "AcDbSymbolTableRecord") '(100 . "AcDbLayerTableRecord") (cons 2 "M-DUCT") '(70 . 0) (cons 62 8) '(6 . "Continuous") (cons 370 13))))
(if (not (tblsearch "LAYER" "E-LIGHT")) (entmake (list '(0 . "LAYER") '(100 . "AcDbSymbolTableRecord") '(100 . "AcDbLayerTableRecord") (cons 2 "E-LIGHT") '(70 . 0) (cons 62 2) '(6 . "Continuous") (cons 370 13))))
(if (not (tblsearch "LAYER" "D-OUTLINE")) (entmake (list '(0 . "LAYER") '(100 . "AcDbSymbolTableRecord") '(100 . "AcDbLayerTableRecord") (cons 2 "D-OUTLINE") '(70 . 0) (cons 62 7) '(6 . "Continuous") (cons 370 30))))
(if (not (tblsearch "LAYER" "D-WALL")) (entmake (list '(0 . "LAYER") '(100 . "AcDbSymbolTableRecord") '(100 . "AcDbLayerTableRecord") (cons 2 "D-WALL") '(70 . 0) (cons 62 7) '(6 . "Continuous") (cons 370 50))))
(if (not (tblsearch "LAYER" "D-HIDDEN")) (entmake (list '(0 . "LAYER") '(100 . "AcDbSymbolTableRecord") '(100 . "AcDbLayerTableRecord") (cons 2 "D-HIDDEN") '(70 . 0) (cons 62 8) '(6 . "Continuous") (cons 370 13))))
(if (not (tblsearch "LAYER" "D-FINE")) (entmake (list '(0 . "LAYER") '(100 . "AcDbSymbolTableRecord") '(100 . "AcDbLayerTableRecord") (cons 2 "D-FINE") '(70 . 0) (cons 62 8) '(6 . "Continuous") (cons 370 13))))
(if (not (tblsearch "LAYER" "D-DIMS")) (entmake (list '(0 . "LAYER") '(100 . "AcDbSymbolTableRecord") '(100 . "AcDbLayerTableRecord") (cons 2 "D-DIMS") '(70 . 0) (cons 62 7) '(6 . "Continuous") (cons 370 13))))
(if (not (tblsearch "LAYER" "D-TEXT")) (entmake (list '(0 . "LAYER") '(100 . "AcDbSymbolTableRecord") '(100 . "AcDbLayerTableRecord") (cons 2 "D-TEXT") '(70 . 0) (cons 62 7) '(6 . "Continuous") (cons 370 13))))
(if (not (tblsearch "LAYER" "D-TITLE")) (entmake (list '(0 . "LAYER") '(100 . "AcDbSymbolTableRecord") '(100 . "AcDbLayerTableRecord") (cons 2 "D-TITLE") '(70 . 0) (cons 62 7) '(6 . "Continuous") (cons 370 35))))
(if (not (tblsearch "LAYER" "D-HATCH")) (entmake (list '(0 . "LAYER") '(100 . "AcDbSymbolTableRecord") '(100 . "AcDbLayerTableRecord") (cons 2 "D-HATCH") '(70 . 0) (cons 62 8) '(6 . "Continuous") (cons 370 9))))
(if (not (tblsearch "LAYER" "D-HOLD")) (entmake (list '(0 . "LAYER") '(100 . "AcDbSymbolTableRecord") '(100 . "AcDbLayerTableRecord") (cons 2 "D-HOLD") '(70 . 0) (cons 62 7) '(6 . "Continuous") (cons 370 18))))
(if (not (tblsearch "LAYER" "VPORT")) (entmake (list '(0 . "LAYER") '(100 . "AcDbSymbolTableRecord") '(100 . "AcDbLayerTableRecord") (cons 2 "VPORT") '(70 . 0) (cons 62 8) '(6 . "Continuous") (cons 370 9))))

(command "_.-LAYER" "_T" "*" "_ON" "*" "")
(foreach ln (layoutlist) (if (and (/= ln "Layout1") (/= ln "Layout2")) (command "_.-LAYOUT" "_D" ln)))
(setvar "TILEMODE" 1)
(command "_.ERASE" "_ALL" "")
(repeat 3 (command "_.-PURGE" "_B" "*" "_N"))
(setvar "TILEMODE" 1)
(setvar "CMDECHO" 0)
(setvar "OSMODE" 0)
(setvar "DYNMODE" 0)
(setvar "INSUNITS" 1)
(setvar "MEASUREMENT" 0)
(setvar "LUNITS" 2)
(setvar "LUPREC" 4)
(setvar "FILEDIA" 0)
(setvar "GRIDMODE" 0)
(setvar "UCSICON" 0)
(command "_.UCS" "_W")
(command "_.PLAN" "_W")
(defun klay (n) (setvar "CLAYER" n))
(defun kbox (a b) (command "_.BOX" a (list (car b) (cadr b) (caddr a)) (- (caddr b) (caddr a))) (entlast))
(defun kname (e n) (entmod (append (entget e) (list (list -3 (list "KITCHEN" (cons 1000 n)))))))
(regapp "KITCHEN")
(if (not (tblsearch "LAYER" "F-CONTEXT")) (entmake (list '(0 . "LAYER") '(100 . "AcDbSymbolTableRecord") '(100 . "AcDbLayerTableRecord") (cons 2 "F-CONTEXT") '(70 . 0) (cons 62 8) '(6 . "Continuous") (cons 370 13))))
(if (not (tblsearch "LAYER" "A-WALL")) (entmake (list '(0 . "LAYER") '(100 . "AcDbSymbolTableRecord") '(100 . "AcDbLayerTableRecord") (cons 2 "A-WALL") '(70 . 0) (cons 62 8) '(6 . "Continuous") (cons 370 35))))
(if (not (tblsearch "LAYER" "A-FLOOR")) (entmake (list '(0 . "LAYER") '(100 . "AcDbSymbolTableRecord") '(100 . "AcDbLayerTableRecord") (cons 2 "A-FLOOR") '(70 . 0) (cons 62 8) '(6 . "Continuous") (cons 370 18))))
(if (not (tblsearch "LAYER" "A-CEILING")) (entmake (list '(0 . "LAYER") '(100 . "AcDbSymbolTableRecord") '(100 . "AcDbLayerTableRecord") (cons 2 "A-CEILING") '(70 . 0) (cons 62 8) '(6 . "Continuous") (cons 370 18))))
(if (not (tblsearch "LAYER" "A-JOINERY")) (entmake (list '(0 . "LAYER") '(100 . "AcDbSymbolTableRecord") '(100 . "AcDbLayerTableRecord") (cons 2 "A-JOINERY") '(70 . 0) (cons 62 7) '(6 . "Continuous") (cons 370 25))))
(if (not (tblsearch "LAYER" "A-GLASS")) (entmake (list '(0 . "LAYER") '(100 . "AcDbSymbolTableRecord") '(100 . "AcDbLayerTableRecord") (cons 2 "A-GLASS") '(70 . 0) (cons 62 4) '(6 . "Continuous") (cons 370 13))))
(if (not (tblsearch "LAYER" "C-CARCASS")) (entmake (list '(0 . "LAYER") '(100 . "AcDbSymbolTableRecord") '(100 . "AcDbLayerTableRecord") (cons 2 "C-CARCASS") '(70 . 0) (cons 62 32) '(6 . "Continuous") (cons 370 18))))
(if (not (tblsearch "LAYER" "C-FRONTS")) (entmake (list '(0 . "LAYER") '(100 . "AcDbSymbolTableRecord") '(100 . "AcDbLayerTableRecord") (cons 2 "C-FRONTS") '(70 . 0) (cons 62 33) '(6 . "Continuous") (cons 370 25))))
(if (not (tblsearch "LAYER" "C-PLINTH")) (entmake (list '(0 . "LAYER") '(100 . "AcDbSymbolTableRecord") '(100 . "AcDbLayerTableRecord") (cons 2 "C-PLINTH") '(70 . 0) (cons 62 8) '(6 . "Continuous") (cons 370 18))))
(if (not (tblsearch "LAYER" "C-HARDWARE")) (entmake (list '(0 . "LAYER") '(100 . "AcDbSymbolTableRecord") '(100 . "AcDbLayerTableRecord") (cons 2 "C-HARDWARE") '(70 . 0) (cons 62 9) '(6 . "Continuous") (cons 370 13))))
(if (not (tblsearch "LAYER" "C-GLASS")) (entmake (list '(0 . "LAYER") '(100 . "AcDbSymbolTableRecord") '(100 . "AcDbLayerTableRecord") (cons 2 "C-GLASS") '(70 . 0) (cons 62 4) '(6 . "Continuous") (cons 370 13))))
(if (not (tblsearch "LAYER" "S-PORCELAIN")) (entmake (list '(0 . "LAYER") '(100 . "AcDbSymbolTableRecord") '(100 . "AcDbLayerTableRecord") (cons 2 "S-PORCELAIN") '(70 . 0) (cons 62 7) '(6 . "Continuous") (cons 370 25))))
(if (not (tblsearch "LAYER" "M-METAL")) (entmake (list '(0 . "LAYER") '(100 . "AcDbSymbolTableRecord") '(100 . "AcDbLayerTableRecord") (cons 2 "M-METAL") '(70 . 0) (cons 62 9) '(6 . "Continuous") (cons 370 18))))
(if (not (tblsearch "LAYER" "M-GLASS")) (entmake (list '(0 . "LAYER") '(100 . "AcDbSymbolTableRecord") '(100 . "AcDbLayerTableRecord") (cons 2 "M-GLASS") '(70 . 0) (cons 62 250) '(6 . "Continuous") (cons 370 13))))
(if (not (tblsearch "LAYER" "M-DUCT")) (entmake (list '(0 . "LAYER") '(100 . "AcDbSymbolTableRecord") '(100 . "AcDbLayerTableRecord") (cons 2 "M-DUCT") '(70 . 0) (cons 62 8) '(6 . "Continuous") (cons 370 13))))
(if (not (tblsearch "LAYER" "E-LIGHT")) (entmake (list '(0 . "LAYER") '(100 . "AcDbSymbolTableRecord") '(100 . "AcDbLayerTableRecord") (cons 2 "E-LIGHT") '(70 . 0) (cons 62 2) '(6 . "Continuous") (cons 370 13))))
(if (not (tblsearch "LAYER" "D-OUTLINE")) (entmake (list '(0 . "LAYER") '(100 . "AcDbSymbolTableRecord") '(100 . "AcDbLayerTableRecord") (cons 2 "D-OUTLINE") '(70 . 0) (cons 62 7) '(6 . "Continuous") (cons 370 30))))
(if (not (tblsearch "LAYER" "D-WALL")) (entmake (list '(0 . "LAYER") '(100 . "AcDbSymbolTableRecord") '(100 . "AcDbLayerTableRecord") (cons 2 "D-WALL") '(70 . 0) (cons 62 7) '(6 . "Continuous") (cons 370 50))))
(if (not (tblsearch "LAYER" "D-HIDDEN")) (entmake (list '(0 . "LAYER") '(100 . "AcDbSymbolTableRecord") '(100 . "AcDbLayerTableRecord") (cons 2 "D-HIDDEN") '(70 . 0) (cons 62 8) '(6 . "Continuous") (cons 370 13))))
(if (not (tblsearch "LAYER" "D-FINE")) (entmake (list '(0 . "LAYER") '(100 . "AcDbSymbolTableRecord") '(100 . "AcDbLayerTableRecord") (cons 2 "D-FINE") '(70 . 0) (cons 62 8) '(6 . "Continuous") (cons 370 13))))
(if (not (tblsearch "LAYER" "D-DIMS")) (entmake (list '(0 . "LAYER") '(100 . "AcDbSymbolTableRecord") '(100 . "AcDbLayerTableRecord") (cons 2 "D-DIMS") '(70 . 0) (cons 62 7) '(6 . "Continuous") (cons 370 13))))
(if (not (tblsearch "LAYER" "D-TEXT")) (entmake (list '(0 . "LAYER") '(100 . "AcDbSymbolTableRecord") '(100 . "AcDbLayerTableRecord") (cons 2 "D-TEXT") '(70 . 0) (cons 62 7) '(6 . "Continuous") (cons 370 13))))
(if (not (tblsearch "LAYER" "D-TITLE")) (entmake (list '(0 . "LAYER") '(100 . "AcDbSymbolTableRecord") '(100 . "AcDbLayerTableRecord") (cons 2 "D-TITLE") '(70 . 0) (cons 62 7) '(6 . "Continuous") (cons 370 35))))
(if (not (tblsearch "LAYER" "D-HATCH")) (entmake (list '(0 . "LAYER") '(100 . "AcDbSymbolTableRecord") '(100 . "AcDbLayerTableRecord") (cons 2 "D-HATCH") '(70 . 0) (cons 62 8) '(6 . "Continuous") (cons 370 9))))
(if (not (tblsearch "LAYER" "D-HOLD")) (entmake (list '(0 . "LAYER") '(100 . "AcDbSymbolTableRecord") '(100 . "AcDbLayerTableRecord") (cons 2 "D-HOLD") '(70 . 0) (cons 62 7) '(6 . "Continuous") (cons 370 18))))
(if (not (tblsearch "LAYER" "VPORT")) (entmake (list '(0 . "LAYER") '(100 . "AcDbSymbolTableRecord") '(100 . "AcDbLayerTableRecord") (cons 2 "VPORT") '(70 . 0) (cons 62 8) '(6 . "Continuous") (cons 370 9))))

(setq ks (ssadd))
(klay "A-FLOOR")
(setq ke (kbox '(-4.000000 -232.000000 -1.000000) '(169.000000 4.000000 0.000000)))
(kname ke "Floor")
(ssadd ke ks)
(klay "A-WALL")
(setq ke (kbox '(-4.000000 0.000000 0.000000) '(169.000000 4.000000 108.000000)))
(kname ke "Back wall")
(ssadd ke ks)
(klay "A-WALL")
(setq ke (kbox '(165.000000 -33.250000 0.000000) '(169.000000 0.000000 108.000000)))
(kname ke "Sink wall")
(ssadd ke ks)
(klay "A-WALL")
(setq ke (kbox '(165.000000 -183.000000 0.000000) '(169.000000 -85.250000 108.000000)))
(kname ke "Sink wall")
(ssadd ke ks)
(klay "A-WALL")
(setq ke (kbox '(165.000000 -85.250000 0.000000) '(169.000000 -33.250000 44.000000)))
(kname ke "Sink wall")
(ssadd ke ks)
(klay "A-WALL")
(setq ke (kbox '(165.000000 -85.250000 92.000000) '(169.000000 -33.250000 108.000000)))
(kname ke "Sink wall")
(ssadd ke ks)
(klay "A-WALL")
(setq ke (kbox '(-4.000000 -113.000000 0.000000) '(0.000000 0.000000 108.000000)))
(kname ke "Left cabinet wall")
(ssadd ke ks)
(klay "0") (command "_.-BLOCK" "ROOM" '(0 0 0) ks "")
(klay "0") (command "_.-INSERT" "ROOM" '(0 0 0) 1 1 0)
(setq ks (ssadd))
(klay "A-WALL")
(setq ke (kbox '(21.500000 -120.250000 0.000000) '(25.500000 -113.000000 108.000000)))
(kname ke "Pocket wall")
(ssadd ke ks)
(klay "A-WALL")
(setq ke (kbox '(21.500000 -192.250000 80.500000) '(25.500000 -120.250000 108.000000)))
(kname ke "Pocket wall")
(ssadd ke ks)
(klay "A-WALL")
(setq ke (kbox '(21.500000 -156.250000 0.000000) '(22.100000 -120.250000 80.500000)))
(kname ke "Pocket wall")
(ssadd ke ks)
(klay "A-WALL")
(setq ke (kbox '(24.900000 -156.250000 0.000000) '(25.500000 -120.250000 80.500000)))
(kname ke "Pocket wall")
(ssadd ke ks)
(klay "A-WALL")
(setq ke (kbox '(21.500000 -231.000000 0.000000) '(25.500000 -192.250000 108.000000)))
(kname ke "Pocket wall")
(ssadd ke ks)
(klay "0") (command "_.-BLOCK" "GARAGE-WALL" '(0 0 0) ks "")
(klay "0") (command "_.-INSERT" "GARAGE-WALL" '(0 0 0) 1 1 0)
(setq ks (ssadd))
(klay "A-CEILING")
(setq ke (kbox '(-4.000000 -183.000000 108.000000) '(169.000000 4.000000 110.000000)))
(kname ke "Ceiling")
(ssadd ke ks)
(klay "0") (command "_.-BLOCK" "CEILING" '(0 0 0) ks "")
(klay "0") (command "_.-INSERT" "CEILING" '(0 0 0) 1 1 0)
(setq ks (ssadd))
(klay "C-CARCASS")
(setq ke (kbox '(35.250000 -23.500000 4.000000) '(36.000000 0.000000 34.500000)))
(kname ke "Carcass panel")
(ssadd ke ks)
(klay "C-CARCASS")
(setq ke (kbox '(57.500000 -23.500000 4.000000) '(58.250000 0.000000 34.500000)))
(kname ke "Carcass panel")
(ssadd ke ks)
(klay "C-CARCASS")
(setq ke (kbox '(36.000000 -23.500000 4.000000) '(57.500000 0.000000 4.750000)))
(kname ke "Carcass panel")
(ssadd ke ks)
(klay "C-CARCASS")
(setq ke (kbox '(36.000000 -0.500000 4.750000) '(57.500000 0.000000 34.500000)))
(kname ke "Carcass panel")
(ssadd ke ks)
(klay "C-CARCASS")
(setq ke (kbox '(36.000000 -2.000000 33.750000) '(57.500000 0.000000 34.500000)))
(kname ke "Carcass panel")
(ssadd ke ks)
(klay "C-CARCASS")
(setq ke (kbox '(36.000000 -23.500000 33.750000) '(57.500000 -21.500000 34.500000)))
(kname ke "Carcass panel")
(ssadd ke ks)
(klay "C-PLINTH")
(setq ke (kbox '(35.250000 -22.250000 0.000000) '(58.250000 -3.000000 4.000000)))
(kname ke "Recessed toe kick")
(ssadd ke ks)
(klay "C-FRONTS")
(setq ke (kbox '(35.312500 -24.250000 4.062500) '(58.187500 -23.500000 15.937500)))
(kname ke "Drawer front")
(ssadd ke ks)
(klay "C-CARCASS")
(setq ke (kbox '(36.750000 -23.250000 5.250000) '(56.750000 -2.000000 5.750000)))
(kname ke "Drawer floor")
(ssadd ke ks)
(klay "C-CARCASS")
(setq ke (kbox '(36.250000 -23.250000 5.250000) '(36.750000 -2.000000 12.250000)))
(kname ke "Drawer box")
(ssadd ke ks)
(klay "C-CARCASS")
(setq ke (kbox '(56.750000 -23.250000 5.250000) '(57.250000 -2.000000 12.250000)))
(kname ke "Drawer box")
(ssadd ke ks)
(klay "C-CARCASS")
(setq ke (kbox '(36.750000 -2.500000 5.750000) '(56.750000 -2.000000 12.250000)))
(kname ke "Drawer box")
(ssadd ke ks)
(klay "C-CARCASS")
(setq ke (kbox '(36.750000 -23.250000 5.750000) '(56.750000 -22.750000 12.250000)))
(kname ke "Drawer box")
(ssadd ke ks)
(klay "C-HARDWARE")
(setq ke (kbox '(36.050000 -23.250000 4.950000) '(36.250000 -2.000000 5.650000)))
(kname ke "Runner profile")
(ssadd ke ks)
(klay "C-HARDWARE")
(setq ke (kbox '(57.250000 -23.250000 4.950000) '(57.450000 -2.000000 5.650000)))
(kname ke "Runner profile")
(ssadd ke ks)
(klay "C-HARDWARE")
(setq ke (kbox '(44.072835 -25.234252 12.860000) '(49.427165 -24.800000 13.140000)))
(kname ke "Nickel pull")
(ssadd ke ks)
(klay "C-HARDWARE")
(setq ke (kbox '(44.720236 -24.850000 12.860000) '(45.000236 -24.250000 13.140000)))
(kname ke "Pull fixing")
(ssadd ke ks)
(klay "C-HARDWARE")
(setq ke (kbox '(48.499764 -24.850000 12.860000) '(48.779764 -24.250000 13.140000)))
(kname ke "Pull fixing")
(ssadd ke ks)
(klay "C-FRONTS")
(setq ke (kbox '(35.312500 -24.250000 16.062500) '(58.187500 -23.500000 25.187500)))
(kname ke "Drawer front")
(ssadd ke ks)
(klay "C-CARCASS")
(setq ke (kbox '(36.750000 -23.250000 17.250000) '(56.750000 -2.000000 17.750000)))
(kname ke "Drawer floor")
(ssadd ke ks)
(klay "C-CARCASS")
(setq ke (kbox '(36.250000 -23.250000 17.250000) '(36.750000 -2.000000 24.000000)))
(kname ke "Drawer box")
(ssadd ke ks)
(klay "C-CARCASS")
(setq ke (kbox '(56.750000 -23.250000 17.250000) '(57.250000 -2.000000 24.000000)))
(kname ke "Drawer box")
(ssadd ke ks)
(klay "C-CARCASS")
(setq ke (kbox '(36.750000 -2.500000 17.750000) '(56.750000 -2.000000 24.000000)))
(kname ke "Drawer box")
(ssadd ke ks)
(klay "C-CARCASS")
(setq ke (kbox '(36.750000 -23.250000 17.750000) '(56.750000 -22.750000 24.000000)))
(kname ke "Drawer box")
(ssadd ke ks)
(klay "C-HARDWARE")
(setq ke (kbox '(36.050000 -23.250000 16.950000) '(36.250000 -2.000000 17.650000)))
(kname ke "Runner profile")
(ssadd ke ks)
(klay "C-HARDWARE")
(setq ke (kbox '(57.250000 -23.250000 16.950000) '(57.450000 -2.000000 17.650000)))
(kname ke "Runner profile")
(ssadd ke ks)
(klay "C-HARDWARE")
(setq ke (kbox '(44.072835 -25.234252 22.110000) '(49.427165 -24.800000 22.390000)))
(kname ke "Nickel pull")
(ssadd ke ks)
(klay "C-HARDWARE")
(setq ke (kbox '(44.720236 -24.850000 22.110000) '(45.000236 -24.250000 22.390000)))
(kname ke "Pull fixing")
(ssadd ke ks)
(klay "C-HARDWARE")
(setq ke (kbox '(48.499764 -24.850000 22.110000) '(48.779764 -24.250000 22.390000)))
(kname ke "Pull fixing")
(ssadd ke ks)
(klay "C-FRONTS")
(setq ke (kbox '(35.312500 -24.250000 25.312500) '(58.187500 -23.500000 34.437500)))
(kname ke "Drawer front")
(ssadd ke ks)
(klay "C-CARCASS")
(setq ke (kbox '(36.750000 -23.250000 26.500000) '(56.750000 -2.000000 27.000000)))
(kname ke "Drawer floor")
(ssadd ke ks)
(klay "C-CARCASS")
(setq ke (kbox '(36.250000 -23.250000 26.500000) '(36.750000 -2.000000 33.250000)))
(kname ke "Drawer box")
(ssadd ke ks)
(klay "C-CARCASS")
(setq ke (kbox '(56.750000 -23.250000 26.500000) '(57.250000 -2.000000 33.250000)))
(kname ke "Drawer box")
(ssadd ke ks)
(klay "C-CARCASS")
(setq ke (kbox '(36.750000 -2.500000 27.000000) '(56.750000 -2.000000 33.250000)))
(kname ke "Drawer box")
(ssadd ke ks)
(klay "C-CARCASS")
(setq ke (kbox '(36.750000 -23.250000 27.000000) '(56.750000 -22.750000 33.250000)))
(kname ke "Drawer box")
(ssadd ke ks)
(klay "C-HARDWARE")
(setq ke (kbox '(36.050000 -23.250000 26.200000) '(36.250000 -2.000000 26.900000)))
(kname ke "Runner profile")
(ssadd ke ks)
(klay "C-HARDWARE")
(setq ke (kbox '(57.250000 -23.250000 26.200000) '(57.450000 -2.000000 26.900000)))
(kname ke "Runner profile")
(ssadd ke ks)
(klay "C-HARDWARE")
(setq ke (kbox '(44.072835 -25.234252 31.360000) '(49.427165 -24.800000 31.640000)))
(kname ke "Nickel pull")
(ssadd ke ks)
(klay "C-HARDWARE")
(setq ke (kbox '(44.720236 -24.850000 31.360000) '(45.000236 -24.250000 31.640000)))
(kname ke "Pull fixing")
(ssadd ke ks)
(klay "C-HARDWARE")
(setq ke (kbox '(48.499764 -24.850000 31.360000) '(48.779764 -24.250000 31.640000)))
(kname ke "Pull fixing")
(ssadd ke ks)
(klay "0") (command "_.-BLOCK" "B-35.25" '(0 0 0) ks "")
(klay "0") (command "_.-INSERT" "B-35.25" '(0 0 0) 1 1 0)
(setq ks (ssadd))
(klay "C-CARCASS")
(setq ke (kbox '(58.250000 -23.500000 4.000000) '(59.000000 0.000000 34.500000)))
(kname ke "Carcass panel")
(ssadd ke ks)
(klay "C-CARCASS")
(setq ke (kbox '(67.500000 -23.500000 4.000000) '(68.250000 0.000000 34.500000)))
(kname ke "Carcass panel")
(ssadd ke ks)
(klay "C-CARCASS")
(setq ke (kbox '(59.000000 -23.500000 4.000000) '(67.500000 0.000000 4.750000)))
(kname ke "Carcass panel")
(ssadd ke ks)
(klay "C-CARCASS")
(setq ke (kbox '(59.000000 -0.500000 4.750000) '(67.500000 0.000000 34.500000)))
(kname ke "Carcass panel")
(ssadd ke ks)
(klay "C-CARCASS")
(setq ke (kbox '(59.000000 -2.000000 33.750000) '(67.500000 0.000000 34.500000)))
(kname ke "Carcass panel")
(ssadd ke ks)
(klay "C-CARCASS")
(setq ke (kbox '(59.000000 -23.500000 33.750000) '(67.500000 -21.500000 34.500000)))
(kname ke "Carcass panel")
(ssadd ke ks)
(klay "C-PLINTH")
(setq ke (kbox '(58.250000 -22.250000 0.000000) '(68.250000 -3.000000 4.000000)))
(kname ke "Recessed toe kick")
(ssadd ke ks)
(klay "C-FRONTS")
(setq ke (kbox '(58.312500 -24.250000 4.062500) '(68.187500 -23.500000 34.437500)))
(kname ke "Full-height pullout front")
(ssadd ke ks)
(klay "C-HARDWARE")
(setq ke (kbox '(59.050000 -23.500000 5.790000) '(59.300000 -3.815000 6.490000)))
(kname ke "500mm runner profile")
(ssadd ke ks)
(klay "C-HARDWARE")
(setq ke (kbox '(67.200000 -23.500000 5.790000) '(67.450000 -3.815000 6.490000)))
(kname ke "500mm runner profile")
(ssadd ke ks)
(klay "C-HARDWARE")
(setq ke (kbox '(59.826770 -4.708660 6.790000) '(66.673230 -4.208660 9.500000)))
(kname ke "RB03 spicepullout drawer1 box back")
(ssadd ke ks)
(klay "C-HARDWARE")
(setq ke (kbox '(59.696770 -23.370000 6.290000) '(66.803220 -4.338660 6.790000)))
(kname ke "RB03 spicepullout drawer1 box bottom")
(ssadd ke ks)
(klay "C-HARDWARE")
(setq ke (kbox '(59.326770 -23.500000 5.790000) '(59.826770 -4.208660 9.500000)))
(kname ke "RB03 spicepullout drawer1 box side")
(ssadd ke ks)
(klay "C-HARDWARE")
(setq ke (kbox '(66.673230 -23.500000 5.790000) '(67.173230 -4.208660 9.500000)))
(kname ke "RB03 spicepullout drawer1 box side.001")
(ssadd ke ks)
(klay "C-HARDWARE")
(setq ke (kbox '(59.826770 -23.500000 6.790000) '(66.673230 -23.000000 33.500000)))
(kname ke "RB03 spicepullout drawer1 box subfront")
(ssadd ke ks)
(klay "C-HARDWARE")
(setq ke (kbox '(60.572830 -25.234250 32.962210) '(65.927170 -25.014250 33.237800)))
(kname ke "Top horizontal nickel pull")
(ssadd ke ks)
(klay "C-HARDWARE")
(setq ke (kbox '(61.035230 -25.234250 32.880000) '(61.685230 -24.250000 33.320000)))
(kname ke "Pull fixing")
(ssadd ke ks)
(klay "C-HARDWARE")
(setq ke (kbox '(64.814770 -25.234250 32.880000) '(65.464770 -24.250000 33.320000)))
(kname ke "Pull fixing")
(ssadd ke ks)
(klay "C-HARDWARE")
(setq ke (kbox '(59.950000 -5.200000 6.790000) '(60.200000 -4.950000 30.750000)))
(kname ke "RB03 spicepullout drawer1 organizer fixed-to-base upright")
(ssadd ke ks)
(klay "C-HARDWARE")
(setq ke (kbox '(59.950000 -22.250000 6.790000) '(60.200000 -22.000000 30.750000)))
(kname ke "RB03 spicepullout drawer1 organizer fixed-to-base upright.001")
(ssadd ke ks)
(klay "C-HARDWARE")
(setq ke (kbox '(66.300000 -5.200000 6.790000) '(66.550000 -4.950000 30.750000)))
(kname ke "RB03 spicepullout drawer1 organizer fixed-to-base upright.002")
(ssadd ke ks)
(klay "C-HARDWARE")
(setq ke (kbox '(66.300000 -22.250000 6.790000) '(66.550000 -22.000000 30.750000)))
(kname ke "RB03 spicepullout drawer1 organizer fixed-to-base upright.003")
(ssadd ke ks)
(klay "C-HARDWARE")
(setq ke (kbox '(59.950000 -22.250000 30.500000) '(60.200000 -4.950000 30.750000)))
(kname ke "RB03 spicepullout drawer1 organizer longitudinal top brace")
(ssadd ke ks)
(klay "C-HARDWARE")
(setq ke (kbox '(66.300000 -22.250000 30.500000) '(66.550000 -4.950000 30.750000)))
(kname ke "RB03 spicepullout drawer1 organizer longitudinal top brace.001")
(ssadd ke ks)
(klay "C-HARDWARE")
(setq ke (kbox '(60.200000 -5.450000 14.600000) '(60.450000 -4.950000 14.750000)))
(kname ke "Spice tier angle support")
(ssadd ke ks)
(klay "C-HARDWARE")
(setq ke (kbox '(60.200000 -22.250000 14.600000) '(60.450000 -21.750000 14.750000)))
(kname ke "Spice tier angle support.001")
(ssadd ke ks)
(klay "C-HARDWARE")
(setq ke (kbox '(66.050000 -5.450000 14.600000) '(66.300000 -4.950000 14.750000)))
(kname ke "Spice tier angle support.002")
(ssadd ke ks)
(klay "C-HARDWARE")
(setq ke (kbox '(66.050000 -22.250000 14.600000) '(66.300000 -21.750000 14.750000)))
(kname ke "Spice tier angle support.003")
(ssadd ke ks)
(klay "C-HARDWARE")
(setq ke (kbox '(60.200000 -5.450000 22.600000) '(60.450000 -4.950000 22.750000)))
(kname ke "Spice tier angle support.004")
(ssadd ke ks)
(klay "C-HARDWARE")
(setq ke (kbox '(60.200000 -22.250000 22.600000) '(60.450000 -21.750000 22.750000)))
(kname ke "Spice tier angle support.005")
(ssadd ke ks)
(klay "C-HARDWARE")
(setq ke (kbox '(66.050000 -5.450000 22.600000) '(66.300000 -4.950000 22.750000)))
(kname ke "Spice tier angle support.006")
(ssadd ke ks)
(klay "C-HARDWARE")
(setq ke (kbox '(66.050000 -22.250000 22.600000) '(66.300000 -21.750000 22.750000)))
(kname ke "Spice tier angle support.007")
(ssadd ke ks)
(klay "C-CARCASS")
(setq ke (kbox '(60.200000 -22.000000 14.750000) '(66.300000 -5.200000 15.100000)))
(kname ke "Spice tier shelf")
(ssadd ke ks)
(klay "C-CARCASS")
(setq ke (kbox '(60.200000 -22.000000 22.750000) '(66.300000 -5.200000 23.100000)))
(kname ke "Spice tier shelf.001")
(ssadd ke ks)
(klay "0") (command "_.-BLOCK" "PULLOUT-SPICE-LEFT" '(0 0 0) ks "")
(klay "0") (command "_.-INSERT" "PULLOUT-SPICE-LEFT" '(0 0 0) 1 1 0)
(setq ks (ssadd))
(klay "C-CARCASS")
(setq ke (kbox '(98.750000 -23.500000 4.000000) '(99.500000 0.000000 34.500000)))
(kname ke "Carcass panel")
(ssadd ke ks)
(klay "C-CARCASS")
(setq ke (kbox '(108.000000 -23.500000 4.000000) '(108.750000 0.000000 34.500000)))
(kname ke "Carcass panel")
(ssadd ke ks)
(klay "C-CARCASS")
(setq ke (kbox '(99.500000 -23.500000 4.000000) '(108.000000 0.000000 4.750000)))
(kname ke "Carcass panel")
(ssadd ke ks)
(klay "C-CARCASS")
(setq ke (kbox '(99.500000 -0.500000 4.750000) '(108.000000 0.000000 34.500000)))
(kname ke "Carcass panel")
(ssadd ke ks)
(klay "C-CARCASS")
(setq ke (kbox '(99.500000 -2.000000 33.750000) '(108.000000 0.000000 34.500000)))
(kname ke "Carcass panel")
(ssadd ke ks)
(klay "C-CARCASS")
(setq ke (kbox '(99.500000 -23.500000 33.750000) '(108.000000 -21.500000 34.500000)))
(kname ke "Carcass panel")
(ssadd ke ks)
(klay "C-PLINTH")
(setq ke (kbox '(98.750000 -22.250000 0.000000) '(108.750000 -3.000000 4.000000)))
(kname ke "Recessed toe kick")
(ssadd ke ks)
(klay "C-FRONTS")
(setq ke (kbox '(98.812500 -24.250000 4.062500) '(108.687500 -23.500000 34.437500)))
(kname ke "Full-height pullout front")
(ssadd ke ks)
(klay "C-HARDWARE")
(setq ke (kbox '(99.550000 -23.500000 5.790000) '(99.800000 -3.815000 6.490000)))
(kname ke "500mm runner profile")
(ssadd ke ks)
(klay "C-HARDWARE")
(setq ke (kbox '(107.700000 -23.500000 5.790000) '(107.950000 -3.815000 6.490000)))
(kname ke "500mm runner profile")
(ssadd ke ks)
(klay "C-HARDWARE")
(setq ke (kbox '(100.700000 -6.250000 22.250000) '(106.800000 -6.000000 22.500000)))
(kname ke "Knife insert bearing cross rail")
(ssadd ke ks)
(klay "C-HARDWARE")
(setq ke (kbox '(100.700000 -10.900000 22.250000) '(106.800000 -10.650000 22.500000)))
(kname ke "Knife insert bearing cross rail.001")
(ssadd ke ks)
(klay "C-HARDWARE")
(setq ke (kbox '(100.450000 -22.250000 22.250000) '(100.700000 -4.950000 22.500000)))
(kname ke "Knife insert load-bearing longitudinal rail")
(ssadd ke ks)
(klay "C-HARDWARE")
(setq ke (kbox '(106.800000 -22.250000 22.250000) '(107.050000 -4.950000 22.500000)))
(kname ke "Knife insert load-bearing longitudinal rail.001")
(ssadd ke ks)
(klay "C-CARCASS")
(setq ke (kbox '(101.350000 -10.900000 22.500000) '(106.150000 -6.000000 28.100000)))
(setq kc (kbox '(102.090000 -10.250000 24.000000) '(102.210000 -6.650000 29.000000)))
(command "_.SUBTRACT" ke "" kc "")
(setq kc (kbox '(103.190000 -10.250000 24.000000) '(103.310000 -6.650000 29.000000)))
(command "_.SUBTRACT" ke "" kc "")
(setq kc (kbox '(104.290000 -10.250000 24.000000) '(104.410000 -6.650000 29.000000)))
(command "_.SUBTRACT" ke "" kc "")
(setq kc (kbox '(105.390000 -10.250000 24.000000) '(105.510000 -6.650000 29.000000)))
(command "_.SUBTRACT" ke "" kc "")
(kname ke "Proposed removable slotted knife block")
(ssadd ke ks)
(klay "M-METAL")
(command "_.CYLINDER" '(103.750000 -15.000000 22.800000) 1.1500000000000057 5.300000000000001)
(setq ke (entlast))
(command "_.CYLINDER" '(103.750000 -15.000000 22.940000) 1.0700000000000056 5.300000000000001)
(setq kc (entlast))
(command "_.SUBTRACT" ke "" kc "")
(kname ke "Proposed removable utensil cup")
(ssadd ke ks)
(klay "M-METAL")
(command "_.CYLINDER" '(103.750000 -19.500000 22.800000) 1.1500000000000057 5.300000000000001)
(setq ke (entlast))
(command "_.CYLINDER" '(103.750000 -19.500000 22.940000) 1.0700000000000056 5.300000000000001)
(setq kc (entlast))
(command "_.SUBTRACT" ke "" kc "")
(kname ke "Proposed removable utensil cup.001")
(ssadd ke ks)
(klay "C-HARDWARE")
(setq ke (kbox '(100.326770 -4.708660 6.790000) '(107.173230 -4.208660 9.500000)))
(kname ke "RB04 utensilpullout drawer1 box back")
(ssadd ke ks)
(klay "C-HARDWARE")
(setq ke (kbox '(100.196770 -23.370000 6.290000) '(107.303230 -4.338660 6.790000)))
(kname ke "RB04 utensilpullout drawer1 box bottom")
(ssadd ke ks)
(klay "C-HARDWARE")
(setq ke (kbox '(99.826770 -23.500000 5.790000) '(100.326770 -4.208660 9.500000)))
(kname ke "RB04 utensilpullout drawer1 box side")
(ssadd ke ks)
(klay "C-HARDWARE")
(setq ke (kbox '(107.173230 -23.500000 5.790000) '(107.673230 -4.208660 9.500000)))
(kname ke "RB04 utensilpullout drawer1 box side.001")
(ssadd ke ks)
(klay "C-HARDWARE")
(setq ke (kbox '(100.326770 -23.500000 6.790000) '(107.173230 -23.000000 33.500000)))
(kname ke "RB04 utensilpullout drawer1 box subfront")
(ssadd ke ks)
(klay "C-HARDWARE")
(setq ke (kbox '(101.072840 -25.234250 32.962210) '(106.427160 -25.014250 33.237800)))
(kname ke "Top horizontal nickel pull")
(ssadd ke ks)
(klay "C-HARDWARE")
(setq ke (kbox '(101.535240 -25.234250 32.880000) '(102.185230 -24.250000 33.320000)))
(kname ke "Pull fixing")
(ssadd ke ks)
(klay "C-HARDWARE")
(setq ke (kbox '(105.314770 -25.234250 32.880000) '(105.964760 -24.250000 33.320000)))
(kname ke "Pull fixing")
(ssadd ke ks)
(klay "C-HARDWARE")
(setq ke (kbox '(100.450000 -5.200000 6.790000) '(100.700000 -4.950000 30.750000)))
(kname ke "RB04 utensilpullout drawer1 organizer fixed-to-base upright")
(ssadd ke ks)
(klay "C-HARDWARE")
(setq ke (kbox '(100.450000 -22.250000 6.790000) '(100.700000 -22.000000 30.750000)))
(kname ke "RB04 utensilpullout drawer1 organizer fixed-to-base upright.001")
(ssadd ke ks)
(klay "C-HARDWARE")
(setq ke (kbox '(106.800000 -5.200000 6.790000) '(107.050000 -4.950000 30.750000)))
(kname ke "RB04 utensilpullout drawer1 organizer fixed-to-base upright.002")
(ssadd ke ks)
(klay "C-HARDWARE")
(setq ke (kbox '(106.800000 -22.250000 6.790000) '(107.050000 -22.000000 30.750000)))
(kname ke "RB04 utensilpullout drawer1 organizer fixed-to-base upright.003")
(ssadd ke ks)
(klay "C-HARDWARE")
(setq ke (kbox '(100.450000 -22.250000 30.500000) '(100.700000 -4.950000 30.750000)))
(kname ke "RB04 utensilpullout drawer1 organizer longitudinal top brace")
(ssadd ke ks)
(klay "C-HARDWARE")
(setq ke (kbox '(106.800000 -22.250000 30.500000) '(107.050000 -4.950000 30.750000)))
(kname ke "RB04 utensilpullout drawer1 organizer longitudinal top brace.001")
(ssadd ke ks)
(klay "M-METAL")
(command "_.TORUS" '(103.750000 -15.000000 28.195000) 1.185 0.095)
(setq ke (entlast))
(kname ke "Utensil cup bearing rim")
(ssadd ke ks)
(klay "M-METAL")
(command "_.TORUS" '(103.750000 -19.500000 28.195000) 1.185 0.095)
(setq ke (entlast))
(kname ke "Utensil cup bearing rim.001")
(ssadd ke ks)
(klay "C-HARDWARE")
(setq ke (kbox '(100.700000 -22.000000 27.750000) '(106.800000 -5.200000 28.100000)))
(setq kc (kbox '(101.25 -11 27) '(106.25 -5.9 29)))
(command "_.SUBTRACT" ke "" kc "")
(command "_.CYLINDER" '(103.750000 -15.000000 27.000000) 1.17 2)
(setq kc (entlast))
(command "_.SUBTRACT" ke "" kc "")
(command "_.CYLINDER" '(103.750000 -19.500000 27.000000) 1.17 2)
(setq kc (entlast))
(command "_.SUBTRACT" ke "" kc "")
(kname ke "Utensil cups supported mounting plate")
(ssadd ke ks)
(klay "0") (command "_.-BLOCK" "PULLOUT-UTENSIL-RIGHT" '(0 0 0) ks "")
(klay "0") (command "_.-INSERT" "PULLOUT-UTENSIL-RIGHT" '(0 0 0) 1 1 0)
(setq ks (ssadd))
(klay "C-CARCASS")
(setq ke (kbox '(108.750000 -23.500000 4.000000) '(109.500000 0.000000 34.500000)))
(kname ke "Carcass panel")
(ssadd ke ks)
(klay "C-CARCASS")
(setq ke (kbox '(137.500000 -23.500000 4.000000) '(138.250000 0.000000 34.500000)))
(kname ke "Carcass panel")
(ssadd ke ks)
(klay "C-CARCASS")
(setq ke (kbox '(109.500000 -23.500000 4.000000) '(137.500000 0.000000 4.750000)))
(kname ke "Carcass panel")
(ssadd ke ks)
(klay "C-CARCASS")
(setq ke (kbox '(109.500000 -0.500000 4.750000) '(137.500000 0.000000 34.500000)))
(kname ke "Carcass panel")
(ssadd ke ks)
(klay "C-CARCASS")
(setq ke (kbox '(109.500000 -2.000000 33.750000) '(137.500000 0.000000 34.500000)))
(kname ke "Carcass panel")
(ssadd ke ks)
(klay "C-CARCASS")
(setq ke (kbox '(109.500000 -23.500000 33.750000) '(137.500000 -21.500000 34.500000)))
(kname ke "Carcass panel")
(ssadd ke ks)
(klay "C-PLINTH")
(setq ke (kbox '(108.750000 -22.250000 0.000000) '(138.250000 -3.000000 4.000000)))
(kname ke "Recessed toe kick")
(ssadd ke ks)
(klay "C-FRONTS")
(setq ke (kbox '(108.812500 -24.250000 4.062500) '(138.187500 -23.500000 15.937500)))
(kname ke "Drawer front")
(ssadd ke ks)
(klay "C-CARCASS")
(setq ke (kbox '(110.250000 -23.250000 5.250000) '(136.750000 -2.000000 5.750000)))
(kname ke "Drawer floor")
(ssadd ke ks)
(klay "C-CARCASS")
(setq ke (kbox '(109.750000 -23.250000 5.250000) '(110.250000 -2.000000 12.250000)))
(kname ke "Drawer box")
(ssadd ke ks)
(klay "C-CARCASS")
(setq ke (kbox '(136.750000 -23.250000 5.250000) '(137.250000 -2.000000 12.250000)))
(kname ke "Drawer box")
(ssadd ke ks)
(klay "C-CARCASS")
(setq ke (kbox '(110.250000 -2.500000 5.750000) '(136.750000 -2.000000 12.250000)))
(kname ke "Drawer box")
(ssadd ke ks)
(klay "C-CARCASS")
(setq ke (kbox '(110.250000 -23.250000 5.750000) '(136.750000 -22.750000 12.250000)))
(kname ke "Drawer box")
(ssadd ke ks)
(klay "C-HARDWARE")
(setq ke (kbox '(109.550000 -23.250000 4.950000) '(109.750000 -2.000000 5.650000)))
(kname ke "Runner profile")
(ssadd ke ks)
(klay "C-HARDWARE")
(setq ke (kbox '(137.250000 -23.250000 4.950000) '(137.450000 -2.000000 5.650000)))
(kname ke "Runner profile")
(ssadd ke ks)
(klay "C-HARDWARE")
(setq ke (kbox '(120.822835 -25.234252 12.860000) '(126.177165 -24.800000 13.140000)))
(kname ke "Nickel pull")
(ssadd ke ks)
(klay "C-HARDWARE")
(setq ke (kbox '(121.470236 -24.850000 12.860000) '(121.750236 -24.250000 13.140000)))
(kname ke "Pull fixing")
(ssadd ke ks)
(klay "C-HARDWARE")
(setq ke (kbox '(125.249764 -24.850000 12.860000) '(125.529764 -24.250000 13.140000)))
(kname ke "Pull fixing")
(ssadd ke ks)
(klay "C-FRONTS")
(setq ke (kbox '(108.812500 -24.250000 16.062500) '(138.187500 -23.500000 25.187500)))
(kname ke "Drawer front")
(ssadd ke ks)
(klay "C-CARCASS")
(setq ke (kbox '(110.250000 -23.250000 17.250000) '(136.750000 -2.000000 17.750000)))
(kname ke "Drawer floor")
(ssadd ke ks)
(klay "C-CARCASS")
(setq ke (kbox '(109.750000 -23.250000 17.250000) '(110.250000 -2.000000 24.000000)))
(kname ke "Drawer box")
(ssadd ke ks)
(klay "C-CARCASS")
(setq ke (kbox '(136.750000 -23.250000 17.250000) '(137.250000 -2.000000 24.000000)))
(kname ke "Drawer box")
(ssadd ke ks)
(klay "C-CARCASS")
(setq ke (kbox '(110.250000 -2.500000 17.750000) '(136.750000 -2.000000 24.000000)))
(kname ke "Drawer box")
(ssadd ke ks)
(klay "C-CARCASS")
(setq ke (kbox '(110.250000 -23.250000 17.750000) '(136.750000 -22.750000 24.000000)))
(kname ke "Drawer box")
(ssadd ke ks)
(klay "C-HARDWARE")
(setq ke (kbox '(109.550000 -23.250000 16.950000) '(109.750000 -2.000000 17.650000)))
(kname ke "Runner profile")
(ssadd ke ks)
(klay "C-HARDWARE")
(setq ke (kbox '(137.250000 -23.250000 16.950000) '(137.450000 -2.000000 17.650000)))
(kname ke "Runner profile")
(ssadd ke ks)
(klay "C-HARDWARE")
(setq ke (kbox '(120.822835 -25.234252 22.110000) '(126.177165 -24.800000 22.390000)))
(kname ke "Nickel pull")
(ssadd ke ks)
(klay "C-HARDWARE")
(setq ke (kbox '(121.470236 -24.850000 22.110000) '(121.750236 -24.250000 22.390000)))
(kname ke "Pull fixing")
(ssadd ke ks)
(klay "C-HARDWARE")
(setq ke (kbox '(125.249764 -24.850000 22.110000) '(125.529764 -24.250000 22.390000)))
(kname ke "Pull fixing")
(ssadd ke ks)
(klay "C-FRONTS")
(setq ke (kbox '(108.812500 -24.250000 25.312500) '(138.187500 -23.500000 34.437500)))
(kname ke "Drawer front")
(ssadd ke ks)
(klay "C-CARCASS")
(setq ke (kbox '(110.250000 -23.250000 26.500000) '(136.750000 -2.000000 27.000000)))
(kname ke "Drawer floor")
(ssadd ke ks)
(klay "C-CARCASS")
(setq ke (kbox '(109.750000 -23.250000 26.500000) '(110.250000 -2.000000 33.250000)))
(kname ke "Drawer box")
(ssadd ke ks)
(klay "C-CARCASS")
(setq ke (kbox '(136.750000 -23.250000 26.500000) '(137.250000 -2.000000 33.250000)))
(kname ke "Drawer box")
(ssadd ke ks)
(klay "C-CARCASS")
(setq ke (kbox '(110.250000 -2.500000 27.000000) '(136.750000 -2.000000 33.250000)))
(kname ke "Drawer box")
(ssadd ke ks)
(klay "C-CARCASS")
(setq ke (kbox '(110.250000 -23.250000 27.000000) '(136.750000 -22.750000 33.250000)))
(kname ke "Drawer box")
(ssadd ke ks)
(klay "C-HARDWARE")
(setq ke (kbox '(109.550000 -23.250000 26.200000) '(109.750000 -2.000000 26.900000)))
(kname ke "Runner profile")
(ssadd ke ks)
(klay "C-HARDWARE")
(setq ke (kbox '(137.250000 -23.250000 26.200000) '(137.450000 -2.000000 26.900000)))
(kname ke "Runner profile")
(ssadd ke ks)
(klay "C-HARDWARE")
(setq ke (kbox '(120.822835 -25.234252 31.360000) '(126.177165 -24.800000 31.640000)))
(kname ke "Nickel pull")
(ssadd ke ks)
(klay "C-HARDWARE")
(setq ke (kbox '(121.470236 -24.850000 31.360000) '(121.750236 -24.250000 31.640000)))
(kname ke "Pull fixing")
(ssadd ke ks)
(klay "C-HARDWARE")
(setq ke (kbox '(125.249764 -24.850000 31.360000) '(125.529764 -24.250000 31.640000)))
(kname ke "Pull fixing")
(ssadd ke ks)
(klay "0") (command "_.-BLOCK" "B-108.75" '(0 0 0) ks "")
(klay "0") (command "_.-INSERT" "B-108.75" '(0 0 0) 1 1 0)
(setq ks (ssadd))
(klay "C-FRONTS")
(setq ke (kbox '(138.250000 -24.250000 4.000000) '(140.750000 0.000000 34.500000)))
(kname ke "Back filler")
(ssadd ke ks)
(klay "0") (command "_.-BLOCK" "B-FILLER" '(0 0 0) ks "")
(klay "0") (command "_.-INSERT" "B-FILLER" '(0 0 0) 1 1 0)
(setq ks (ssadd))
(klay "C-CARCASS")
(setq ke (kbox '(0.000000 -24.250000 4.000000) '(35.250000 0.000000 4.750000)))
(kname ke "L corner carcass")
(ssadd ke ks)
(klay "C-CARCASS")
(setq ke (kbox '(0.000000 -35.250000 4.000000) '(25.500000 -24.250000 4.750000)))
(kname ke "L corner carcass")
(ssadd ke ks)
(klay "C-CARCASS")
(setq ke (kbox '(0.000000 -35.250000 4.750000) '(0.750000 0.000000 34.500000)))
(kname ke "L corner carcass")
(ssadd ke ks)
(klay "C-CARCASS")
(setq ke (kbox '(0.750000 -0.500000 4.750000) '(35.250000 0.000000 34.500000)))
(kname ke "L corner carcass")
(ssadd ke ks)
(klay "C-CARCASS")
(setq ke (kbox '(34.500000 -23.500000 4.750000) '(35.250000 -0.500000 34.500000)))
(kname ke "L corner carcass")
(ssadd ke ks)
(klay "C-CARCASS")
(setq ke (kbox '(0.750000 -35.250000 4.750000) '(24.750000 -34.500000 34.500000)))
(kname ke "L corner carcass")
(ssadd ke ks)
(klay "C-FRONTS")
(setq ke (kbox '(25.562500 -24.250000 4.062500) '(35.187500 -23.500000 34.437500)))
(kname ke "Corner door")
(ssadd ke ks)
(klay "C-FRONTS")
(setq ke (kbox '(24.750000 -35.187500 4.062500) '(25.500000 -24.312500 34.437500)))
(kname ke "Corner door")
(ssadd ke ks)
(klay "C-PLINTH")
(setq ke (kbox '(25.500000 -22.000000 0.000000) '(35.250000 -21.250000 4.000000)))
(kname ke "Corner toe kick")
(ssadd ke ks)
(klay "C-PLINTH")
(setq ke (kbox '(22.500000 -35.250000 0.000000) '(23.250000 -24.250000 4.000000)))
(kname ke "Corner toe kick")
(ssadd ke ks)
(klay "0") (command "_.-BLOCK" "BASE-LEFT-CORNER" '(0 0 0) ks "")
(klay "0") (command "_.-INSERT" "BASE-LEFT-CORNER" '(0 0 0) 1 1 0)
(setq ks (ssadd))
(klay "C-FRONTS")
(setq ke (kbox '(0.000000 -36.000000 0.000000) '(25.500000 -35.250000 108.000000)))
(kname ke "Tall end panel")
(ssadd ke ks)
(klay "C-FRONTS")
(setq ke (kbox '(0.000000 -73.500000 0.000000) '(25.500000 -72.750000 108.000000)))
(kname ke "Tall end panel")
(ssadd ke ks)
(klay "C-FRONTS")
(setq ke (kbox '(0.000000 -113.000000 0.000000) '(25.500000 -110.500000 108.000000)))
(kname ke "Tall end panel")
(ssadd ke ks)
(klay "C-FRONTS")
(setq ke (kbox '(0.000000 -72.750000 106.000000) '(25.500000 -36.000000 108.000000)))
(kname ke "Fridge top filler")
(ssadd ke ks)
(klay "C-FRONTS")
(setq ke (kbox '(0.000000 -110.500000 106.000000) '(25.500000 -73.500000 108.000000)))
(kname ke "Pantry top filler")
(ssadd ke ks)
(klay "0") (command "_.-BLOCK" "LEFT-PANELS" '(0 0 0) ks "")
(klay "0") (command "_.-INSERT" "LEFT-PANELS" '(0 0 0) 1 1 0)
(setq ks (ssadd))
(klay "C-CARCASS")
(setq ke (kbox '(0.000000 -36.750000 71.000000) '(24.750000 -36.000000 106.000000)))
(kname ke "Carcass panel")
(ssadd ke ks)
(klay "C-CARCASS")
(setq ke (kbox '(0.000000 -72.750000 71.000000) '(24.750000 -72.000000 106.000000)))
(kname ke "Carcass panel")
(ssadd ke ks)
(klay "C-CARCASS")
(setq ke (kbox '(0.000000 -72.000000 71.000000) '(24.750000 -36.750000 71.750000)))
(kname ke "Carcass panel")
(ssadd ke ks)
(klay "C-CARCASS")
(setq ke (kbox '(0.000000 -72.000000 71.750000) '(0.500000 -36.750000 106.000000)))
(kname ke "Carcass panel")
(ssadd ke ks)
(klay "C-CARCASS")
(setq ke (kbox '(0.000000 -72.000000 105.250000) '(2.000000 -36.750000 106.000000)))
(kname ke "Carcass panel")
(ssadd ke ks)
(klay "C-CARCASS")
(setq ke (kbox '(22.750000 -72.000000 105.250000) '(24.750000 -36.750000 106.000000)))
(kname ke "Carcass panel")
(ssadd ke ks)
(klay "C-FRONTS")
(setq ke (kbox '(24.750000 -54.312500 71.062500) '(25.500000 -36.062500 105.937500)))
(kname ke "Door front")
(ssadd ke ks)
(klay "C-HARDWARE")
(setq ke (kbox '(26.050000 -52.515000 85.822835) '(26.484252 -52.235000 91.177165)))
(kname ke "Nickel pull")
(ssadd ke ks)
(klay "C-HARDWARE")
(setq ke (kbox '(25.500000 -52.515000 86.470236) '(26.100000 -52.235000 86.750236)))
(kname ke "Pull fixing")
(ssadd ke ks)
(klay "C-HARDWARE")
(setq ke (kbox '(25.500000 -52.515000 90.249764) '(26.100000 -52.235000 90.529764)))
(kname ke "Pull fixing")
(ssadd ke ks)
(klay "C-HARDWARE")
(setq ke (kbox '(23.500000 -38.250000 75.200000) '(24.750000 -36.750000 76.800000)))
(kname ke "Concealed hinge")
(ssadd ke ks)
(klay "C-HARDWARE")
(setq ke (kbox '(23.500000 -38.250000 100.200000) '(24.750000 -36.750000 101.800000)))
(kname ke "Concealed hinge")
(ssadd ke ks)
(klay "C-FRONTS")
(setq ke (kbox '(24.750000 -72.687500 71.062500) '(25.500000 -54.437500 105.937500)))
(kname ke "Door front")
(ssadd ke ks)
(klay "C-HARDWARE")
(setq ke (kbox '(26.050000 -56.515000 85.822835) '(26.484252 -56.235000 91.177165)))
(kname ke "Nickel pull")
(ssadd ke ks)
(klay "C-HARDWARE")
(setq ke (kbox '(25.500000 -56.515000 86.470236) '(26.100000 -56.235000 86.750236)))
(kname ke "Pull fixing")
(ssadd ke ks)
(klay "C-HARDWARE")
(setq ke (kbox '(25.500000 -56.515000 90.249764) '(26.100000 -56.235000 90.529764)))
(kname ke "Pull fixing")
(ssadd ke ks)
(klay "C-HARDWARE")
(setq ke (kbox '(23.500000 -56.625000 75.200000) '(24.750000 -55.125000 76.800000)))
(kname ke "Concealed hinge")
(ssadd ke ks)
(klay "C-HARDWARE")
(setq ke (kbox '(23.500000 -56.625000 100.200000) '(24.750000 -55.125000 101.800000)))
(kname ke "Concealed hinge")
(ssadd ke ks)
(klay "C-CARCASS")
(setq ke (kbox '(0.500000 -72.000000 88.500000) '(24.500000 -36.750000 89.250000)))
(kname ke "Fixed shelf")
(ssadd ke ks)
(klay "0") (command "_.-BLOCK" "FRIDGE-UPPER" '(0 0 0) ks "")
(klay "0") (command "_.-INSERT" "FRIDGE-UPPER" '(0 0 0) 1 1 0)
(setq ks (ssadd))
(klay "C-CARCASS")
(setq ke (kbox '(0.000000 -74.250000 4.000000) '(24.750000 -73.500000 20.000000)))
(kname ke "Carcass panel")
(ssadd ke ks)
(klay "C-CARCASS")
(setq ke (kbox '(0.000000 -110.500000 4.000000) '(24.750000 -109.750000 20.000000)))
(kname ke "Carcass panel")
(ssadd ke ks)
(klay "C-CARCASS")
(setq ke (kbox '(0.000000 -109.750000 4.000000) '(24.750000 -74.250000 4.750000)))
(kname ke "Carcass panel")
(ssadd ke ks)
(klay "C-CARCASS")
(setq ke (kbox '(0.000000 -109.750000 4.750000) '(0.500000 -74.250000 20.000000)))
(kname ke "Carcass panel")
(ssadd ke ks)
(klay "C-CARCASS")
(setq ke (kbox '(0.000000 -109.750000 19.250000) '(2.000000 -74.250000 20.000000)))
(kname ke "Carcass panel")
(ssadd ke ks)
(klay "C-CARCASS")
(setq ke (kbox '(22.750000 -109.750000 19.250000) '(24.750000 -74.250000 20.000000)))
(kname ke "Carcass panel")
(ssadd ke ks)
(klay "C-PLINTH")
(setq ke (kbox '(3.000000 -110.500000 0.000000) '(23.500000 -73.500000 4.000000)))
(kname ke "Recessed toe kick")
(ssadd ke ks)
(klay "C-FRONTS")
(setq ke (kbox '(24.750000 -110.437500 4.062500) '(25.500000 -73.562500 19.937500)))
(kname ke "Drawer front")
(ssadd ke ks)
(klay "C-CARCASS")
(setq ke (kbox '(2.000000 -109.000000 5.250000) '(24.500000 -75.000000 5.750000)))
(kname ke "Drawer floor")
(ssadd ke ks)
(klay "C-CARCASS")
(setq ke (kbox '(2.000000 -75.000000 5.250000) '(24.500000 -74.500000 12.250000)))
(kname ke "Drawer box")
(ssadd ke ks)
(klay "C-CARCASS")
(setq ke (kbox '(2.000000 -109.500000 5.250000) '(24.500000 -109.000000 12.250000)))
(kname ke "Drawer box")
(ssadd ke ks)
(klay "C-CARCASS")
(setq ke (kbox '(2.000000 -109.000000 5.750000) '(2.500000 -75.000000 12.250000)))
(kname ke "Drawer box")
(ssadd ke ks)
(klay "C-CARCASS")
(setq ke (kbox '(24.000000 -109.000000 5.750000) '(24.500000 -75.000000 12.250000)))
(kname ke "Drawer box")
(ssadd ke ks)
(klay "C-HARDWARE")
(setq ke (kbox '(2.000000 -74.500000 4.950000) '(24.500000 -74.300000 5.650000)))
(kname ke "Runner profile")
(ssadd ke ks)
(klay "C-HARDWARE")
(setq ke (kbox '(2.000000 -109.700000 4.950000) '(24.500000 -109.500000 5.650000)))
(kname ke "Runner profile")
(ssadd ke ks)
(klay "C-HARDWARE")
(setq ke (kbox '(26.050000 -94.677165 16.860000) '(26.484252 -89.322835 17.140000)))
(kname ke "Nickel pull")
(ssadd ke ks)
(klay "C-HARDWARE")
(setq ke (kbox '(25.500000 -90.250236 16.860000) '(26.100000 -89.970236 17.140000)))
(kname ke "Pull fixing")
(ssadd ke ks)
(klay "C-HARDWARE")
(setq ke (kbox '(25.500000 -94.029764 16.860000) '(26.100000 -93.749764 17.140000)))
(kname ke "Pull fixing")
(ssadd ke ks)
(klay "0") (command "_.-BLOCK" "PANTRY-LOWER" '(0 0 0) ks "")
(klay "0") (command "_.-INSERT" "PANTRY-LOWER" '(0 0 0) 1 1 0)
(setq ks (ssadd))
(klay "C-CARCASS")
(setq ke (kbox '(0.000000 -74.250000 71.000000) '(24.750000 -73.500000 106.000000)))
(kname ke "Carcass panel")
(ssadd ke ks)
(klay "C-CARCASS")
(setq ke (kbox '(0.000000 -110.500000 71.000000) '(24.750000 -109.750000 106.000000)))
(kname ke "Carcass panel")
(ssadd ke ks)
(klay "C-CARCASS")
(setq ke (kbox '(0.000000 -109.750000 71.000000) '(24.750000 -74.250000 71.750000)))
(kname ke "Carcass panel")
(ssadd ke ks)
(klay "C-CARCASS")
(setq ke (kbox '(0.000000 -109.750000 71.750000) '(0.500000 -74.250000 106.000000)))
(kname ke "Carcass panel")
(ssadd ke ks)
(klay "C-CARCASS")
(setq ke (kbox '(0.000000 -109.750000 105.250000) '(2.000000 -74.250000 106.000000)))
(kname ke "Carcass panel")
(ssadd ke ks)
(klay "C-CARCASS")
(setq ke (kbox '(22.750000 -109.750000 105.250000) '(24.750000 -74.250000 106.000000)))
(kname ke "Carcass panel")
(ssadd ke ks)
(klay "C-FRONTS")
(setq ke (kbox '(24.750000 -91.937500 71.062500) '(25.500000 -73.562500 105.937500)))
(kname ke "Door front")
(ssadd ke ks)
(klay "C-HARDWARE")
(setq ke (kbox '(26.050000 -90.140000 85.822835) '(26.484252 -89.860000 91.177165)))
(kname ke "Nickel pull")
(ssadd ke ks)
(klay "C-HARDWARE")
(setq ke (kbox '(25.500000 -90.140000 86.470236) '(26.100000 -89.860000 86.750236)))
(kname ke "Pull fixing")
(ssadd ke ks)
(klay "C-HARDWARE")
(setq ke (kbox '(25.500000 -90.140000 90.249764) '(26.100000 -89.860000 90.529764)))
(kname ke "Pull fixing")
(ssadd ke ks)
(klay "C-HARDWARE")
(setq ke (kbox '(23.500000 -75.750000 75.200000) '(24.750000 -74.250000 76.800000)))
(kname ke "Concealed hinge")
(ssadd ke ks)
(klay "C-HARDWARE")
(setq ke (kbox '(23.500000 -75.750000 100.200000) '(24.750000 -74.250000 101.800000)))
(kname ke "Concealed hinge")
(ssadd ke ks)
(klay "C-FRONTS")
(setq ke (kbox '(24.750000 -110.437500 71.062500) '(25.500000 -92.062500 105.937500)))
(kname ke "Door front")
(ssadd ke ks)
(klay "C-HARDWARE")
(setq ke (kbox '(26.050000 -94.140000 85.822835) '(26.484252 -93.860000 91.177165)))
(kname ke "Nickel pull")
(ssadd ke ks)
(klay "C-HARDWARE")
(setq ke (kbox '(25.500000 -94.140000 86.470236) '(26.100000 -93.860000 86.750236)))
(kname ke "Pull fixing")
(ssadd ke ks)
(klay "C-HARDWARE")
(setq ke (kbox '(25.500000 -94.140000 90.249764) '(26.100000 -93.860000 90.529764)))
(kname ke "Pull fixing")
(ssadd ke ks)
(klay "C-HARDWARE")
(setq ke (kbox '(23.500000 -94.250000 75.200000) '(24.750000 -92.750000 76.800000)))
(kname ke "Concealed hinge")
(ssadd ke ks)
(klay "C-HARDWARE")
(setq ke (kbox '(23.500000 -94.250000 100.200000) '(24.750000 -92.750000 101.800000)))
(kname ke "Concealed hinge")
(ssadd ke ks)
(klay "C-CARCASS")
(setq ke (kbox '(0.500000 -109.750000 88.500000) '(24.500000 -74.250000 89.250000)))
(kname ke "Fixed shelf")
(ssadd ke ks)
(klay "0") (command "_.-BLOCK" "PANTRY-UPPER" '(0 0 0) ks "")
(klay "0") (command "_.-INSERT" "PANTRY-UPPER" '(0 0 0) 1 1 0)
(setq ks (ssadd))
(klay "C-CARCASS")
(setq ke (kbox '(0.000000 -74.250000 20.000000) '(24.750000 -73.500000 71.000000)))
(kname ke "Pocket partition")
(ssadd ke ks)
(klay "C-CARCASS")
(setq ke (kbox '(0.000000 -110.500000 20.000000) '(24.750000 -109.750000 71.000000)))
(kname ke "Pocket partition")
(ssadd ke ks)
(klay "C-CARCASS")
(setq ke (kbox '(0.000000 -76.550000 20.000000) '(24.750000 -76.050000 71.000000)))
(kname ke "Pocket partition")
(ssadd ke ks)
(klay "C-CARCASS")
(setq ke (kbox '(0.000000 -107.950000 20.000000) '(24.750000 -107.450000 71.000000)))
(kname ke "Pocket partition")
(ssadd ke ks)
(klay "C-CARCASS")
(setq ke (kbox '(0.000000 -109.750000 20.000000) '(0.500000 -74.250000 71.000000)))
(kname ke "Pocket bay back")
(ssadd ke ks)
(klay "C-CARCASS")
(setq ke (kbox '(0.500000 -107.450000 39.000000) '(24.500000 -76.550000 39.750000)))
(kname ke "Fixed upper shelf")
(ssadd ke ks)
(klay "C-CARCASS")
(setq ke (kbox '(0.500000 -107.450000 56.000000) '(24.500000 -76.550000 56.750000)))
(kname ke "Fixed upper shelf")
(ssadd ke ks)
(klay "0") (command "_.-BLOCK" "PANTRY-COFFEE" '(0 0 0) ks "")
(klay "0") (command "_.-INSERT" "PANTRY-COFFEE" '(0 0 0) 1 1 0)
(setq ks (ssadd))
(klay "C-FRONTS")
(setq ke (kbox '(24.750000 -91.937500 20.062500) '(25.500000 -73.562500 70.937500)))
(kname ke "Pocket leaf")
(ssadd ke ks)
(klay "C-FRONTS")
(setq ke (kbox '(24.750000 -110.437500 20.062500) '(25.500000 -92.062500 70.937500)))
(kname ke "Pocket leaf")
(ssadd ke ks)
(klay "0") (command "_.-BLOCK" "PANTRY-POCKET-DOORS" '(0 0 0) ks "")
(klay "0") (command "_.-INSERT" "PANTRY-POCKET-DOORS" '(0 0 0) 1 1 0)
(setq ks (ssadd))
(klay "C-CARCASS")
(setq ke (kbox '(4.500000 -106.950000 21.750000) '(24.200000 -77.050000 22.500000)))
(kname ke "Lowest pullout tray")
(ssadd ke ks)
(klay "C-HARDWARE")
(setq ke (kbox '(4.500000 -76.950000 21.000000) '(24.200000 -76.650000 21.750000)))
(kname ke "500mm runner profile")
(ssadd ke ks)
(klay "C-HARDWARE")
(setq ke (kbox '(4.500000 -107.350000 21.000000) '(24.200000 -107.050000 21.750000)))
(kname ke "500mm runner profile")
(ssadd ke ks)
(klay "0") (command "_.-BLOCK" "PANTRY-LOWEST-TRAY" '(0 0 0) ks "")
(klay "0") (command "_.-INSERT" "PANTRY-LOWEST-TRAY" '(0 0 0) 1 1 0)
(setq ks (ssadd))
(klay "C-CARCASS")
(setq ke (kbox '(141.500000 -0.750000 4.000000) '(165.000000 0.000000 34.500000)))
(kname ke "Carcass panel")
(ssadd ke ks)
(klay "C-CARCASS")
(setq ke (kbox '(141.500000 -26.000000 4.000000) '(165.000000 -25.250000 34.500000)))
(kname ke "Carcass panel")
(ssadd ke ks)
(klay "C-CARCASS")
(setq ke (kbox '(141.500000 -25.250000 4.000000) '(165.000000 -0.750000 4.750000)))
(kname ke "Carcass panel")
(ssadd ke ks)
(klay "C-CARCASS")
(setq ke (kbox '(164.500000 -25.250000 4.750000) '(165.000000 -0.750000 34.500000)))
(kname ke "Carcass panel")
(ssadd ke ks)
(klay "C-CARCASS")
(setq ke (kbox '(163.000000 -25.250000 33.750000) '(165.000000 -0.750000 34.500000)))
(kname ke "Carcass panel")
(ssadd ke ks)
(klay "C-CARCASS")
(setq ke (kbox '(141.500000 -25.250000 33.750000) '(143.500000 -0.750000 34.500000)))
(kname ke "Carcass panel")
(ssadd ke ks)
(klay "C-PLINTH")
(setq ke (kbox '(142.750000 -26.000000 0.000000) '(162.000000 0.000000 4.000000)))
(kname ke "Recessed toe kick")
(ssadd ke ks)
(klay "C-FRONTS")
(setq ke (kbox '(140.750000 -25.937500 4.062500) '(141.500000 -0.062500 34.437500)))
(kname ke "Door front")
(ssadd ke ks)
(klay "C-HARDWARE")
(setq ke (kbox '(139.765748 -24.140000 16.572835) '(140.200000 -23.860000 21.927165)))
(kname ke "Nickel pull")
(ssadd ke ks)
(klay "C-HARDWARE")
(setq ke (kbox '(140.150000 -24.140000 17.220236) '(140.750000 -23.860000 17.500236)))
(kname ke "Pull fixing")
(ssadd ke ks)
(klay "C-HARDWARE")
(setq ke (kbox '(140.150000 -24.140000 20.999764) '(140.750000 -23.860000 21.279764)))
(kname ke "Pull fixing")
(ssadd ke ks)
(klay "C-HARDWARE")
(setq ke (kbox '(141.500000 -2.250000 8.200000) '(142.750000 -0.750000 9.800000)))
(kname ke "Concealed hinge")
(ssadd ke ks)
(klay "C-HARDWARE")
(setq ke (kbox '(141.500000 -2.250000 28.700000) '(142.750000 -0.750000 30.300000)))
(kname ke "Concealed hinge")
(ssadd ke ks)
(klay "C-CARCASS")
(setq ke (kbox '(141.750000 -25.250000 19.250000) '(164.500000 -0.750000 20.000000)))
(kname ke "Fixed shelf")
(ssadd ke ks)
(klay "0") (command "_.-BLOCK" "S-0" '(0 0 0) ks "")
(klay "0") (command "_.-INSERT" "S-0" '(0 0 0) 1 1 0)
(setq ks (ssadd))
(klay "C-CARCASS")
(setq ke (kbox '(141.500000 -26.750000 4.000000) '(165.000000 -26.000000 34.500000)))
(kname ke "Carcass panel")
(ssadd ke ks)
(klay "C-CARCASS")
(setq ke (kbox '(141.500000 -41.000000 4.000000) '(165.000000 -40.250000 34.500000)))
(kname ke "Carcass panel")
(ssadd ke ks)
(klay "C-CARCASS")
(setq ke (kbox '(141.500000 -40.250000 4.000000) '(165.000000 -26.750000 4.750000)))
(kname ke "Carcass panel")
(ssadd ke ks)
(klay "C-CARCASS")
(setq ke (kbox '(164.500000 -40.250000 4.750000) '(165.000000 -26.750000 34.500000)))
(kname ke "Carcass panel")
(ssadd ke ks)
(klay "C-CARCASS")
(setq ke (kbox '(163.000000 -40.250000 33.750000) '(165.000000 -26.750000 34.500000)))
(kname ke "Carcass panel")
(ssadd ke ks)
(klay "C-CARCASS")
(setq ke (kbox '(141.500000 -40.250000 33.750000) '(143.500000 -26.750000 34.500000)))
(kname ke "Carcass panel")
(ssadd ke ks)
(klay "C-PLINTH")
(setq ke (kbox '(142.750000 -41.000000 0.000000) '(162.000000 -26.000000 4.000000)))
(kname ke "Recessed toe kick")
(ssadd ke ks)
(klay "C-FRONTS")
(setq ke (kbox '(140.750000 -40.937500 4.062500) '(141.500000 -26.062500 34.437500)))
(kname ke "Door front")
(ssadd ke ks)
(klay "C-HARDWARE")
(setq ke (kbox '(139.765748 -39.140000 16.572835) '(140.200000 -38.860000 21.927165)))
(kname ke "Nickel pull")
(ssadd ke ks)
(klay "C-HARDWARE")
(setq ke (kbox '(140.150000 -39.140000 17.220236) '(140.750000 -38.860000 17.500236)))
(kname ke "Pull fixing")
(ssadd ke ks)
(klay "C-HARDWARE")
(setq ke (kbox '(140.150000 -39.140000 20.999764) '(140.750000 -38.860000 21.279764)))
(kname ke "Pull fixing")
(ssadd ke ks)
(klay "C-HARDWARE")
(setq ke (kbox '(141.500000 -28.250000 8.200000) '(142.750000 -26.750000 9.800000)))
(kname ke "Concealed hinge")
(ssadd ke ks)
(klay "C-HARDWARE")
(setq ke (kbox '(141.500000 -28.250000 28.700000) '(142.750000 -26.750000 30.300000)))
(kname ke "Concealed hinge")
(ssadd ke ks)
(klay "C-CARCASS")
(setq ke (kbox '(141.750000 -40.250000 19.250000) '(164.500000 -26.750000 20.000000)))
(kname ke "Fixed shelf")
(ssadd ke ks)
(klay "0") (command "_.-BLOCK" "S-26" '(0 0 0) ks "")
(klay "0") (command "_.-INSERT" "S-26" '(0 0 0) 1 1 0)
(setq ks (ssadd))
(klay "C-CARCASS")
(setq ke (kbox '(141.500000 -41.750000 4.000000) '(165.000000 -41.000000 34.500000)))
(kname ke "Carcass panel")
(ssadd ke ks)
(klay "C-CARCASS")
(setq ke (kbox '(141.500000 -77.000000 4.000000) '(165.000000 -76.250000 34.500000)))
(kname ke "Carcass panel")
(ssadd ke ks)
(klay "C-CARCASS")
(setq ke (kbox '(141.500000 -76.250000 4.000000) '(165.000000 -41.750000 4.750000)))
(kname ke "Carcass panel")
(ssadd ke ks)
(klay "C-CARCASS")
(setq ke (kbox '(164.500000 -76.250000 4.750000) '(165.000000 -41.750000 34.500000)))
(kname ke "Carcass panel")
(ssadd ke ks)
(klay "C-CARCASS")
(setq ke (kbox '(163.000000 -76.250000 33.750000) '(165.000000 -41.750000 34.500000)))
(kname ke "Carcass panel")
(ssadd ke ks)
(klay "C-CARCASS")
(setq ke (kbox '(141.500000 -76.250000 33.750000) '(143.500000 -41.750000 34.500000)))
(setq kc (kbox '(142 -74.25 26) '(161 -44.25 37)))
(command "_.SUBTRACT" ke "" kc "")
(kname ke "Carcass panel")
(ssadd ke ks)
(klay "C-PLINTH")
(setq ke (kbox '(142.750000 -77.000000 0.000000) '(162.000000 -41.000000 4.000000)))
(kname ke "Recessed toe kick")
(ssadd ke ks)
(klay "C-FRONTS")
(setq ke (kbox '(140.750000 -58.937500 4.062500) '(141.500000 -41.062500 34.437500)))
(kname ke "Door front")
(ssadd ke ks)
(klay "C-HARDWARE")
(setq ke (kbox '(139.765748 -57.140000 16.572835) '(140.200000 -56.860000 21.927165)))
(kname ke "Nickel pull")
(ssadd ke ks)
(klay "C-HARDWARE")
(setq ke (kbox '(140.150000 -57.140000 17.220236) '(140.750000 -56.860000 17.500236)))
(kname ke "Pull fixing")
(ssadd ke ks)
(klay "C-HARDWARE")
(setq ke (kbox '(140.150000 -57.140000 20.999764) '(140.750000 -56.860000 21.279764)))
(kname ke "Pull fixing")
(ssadd ke ks)
(klay "C-HARDWARE")
(setq ke (kbox '(141.500000 -43.250000 8.200000) '(142.750000 -41.750000 9.800000)))
(kname ke "Concealed hinge")
(ssadd ke ks)
(klay "C-HARDWARE")
(setq ke (kbox '(141.500000 -43.250000 28.700000) '(142.750000 -41.750000 30.300000)))
(kname ke "Concealed hinge")
(ssadd ke ks)
(klay "C-FRONTS")
(setq ke (kbox '(140.750000 -76.937500 4.062500) '(141.500000 -59.062500 34.437500)))
(kname ke "Door front")
(ssadd ke ks)
(klay "C-HARDWARE")
(setq ke (kbox '(139.765748 -61.140000 16.572835) '(140.200000 -60.860000 21.927165)))
(kname ke "Nickel pull")
(ssadd ke ks)
(klay "C-HARDWARE")
(setq ke (kbox '(140.150000 -61.140000 17.220236) '(140.750000 -60.860000 17.500236)))
(kname ke "Pull fixing")
(ssadd ke ks)
(klay "C-HARDWARE")
(setq ke (kbox '(140.150000 -61.140000 20.999764) '(140.750000 -60.860000 21.279764)))
(kname ke "Pull fixing")
(ssadd ke ks)
(klay "C-HARDWARE")
(setq ke (kbox '(141.500000 -61.250000 8.200000) '(142.750000 -59.750000 9.800000)))
(kname ke "Concealed hinge")
(ssadd ke ks)
(klay "C-HARDWARE")
(setq ke (kbox '(141.500000 -61.250000 28.700000) '(142.750000 -59.750000 30.300000)))
(setq kc (kbox '(142 -74.25 26) '(161 -44.25 37)))
(command "_.SUBTRACT" ke "" kc "")
(kname ke "Concealed hinge")
(ssadd ke ks)
(klay "C-CARCASS")
(setq ke (kbox '(141.750000 -76.250000 19.250000) '(164.500000 -41.750000 20.000000)))
(kname ke "Fixed shelf")
(ssadd ke ks)
(klay "0") (command "_.-BLOCK" "S-41" '(0 0 0) ks "")
(klay "0") (command "_.-INSERT" "S-41" '(0 0 0) 1 1 0)
(setq ks (ssadd))
(klay "C-CARCASS")
(setq ke (kbox '(141.500000 -77.750000 4.000000) '(165.000000 -77.000000 34.500000)))
(kname ke "Carcass panel")
(ssadd ke ks)
(klay "C-CARCASS")
(setq ke (kbox '(141.500000 -92.000000 4.000000) '(165.000000 -91.250000 34.500000)))
(kname ke "Carcass panel")
(ssadd ke ks)
(klay "C-CARCASS")
(setq ke (kbox '(141.500000 -91.250000 4.000000) '(165.000000 -77.750000 4.750000)))
(kname ke "Carcass panel")
(ssadd ke ks)
(klay "C-CARCASS")
(setq ke (kbox '(164.500000 -91.250000 4.750000) '(165.000000 -77.750000 34.500000)))
(kname ke "Carcass panel")
(ssadd ke ks)
(klay "C-CARCASS")
(setq ke (kbox '(163.000000 -91.250000 33.750000) '(165.000000 -77.750000 34.500000)))
(kname ke "Carcass panel")
(ssadd ke ks)
(klay "C-CARCASS")
(setq ke (kbox '(141.500000 -91.250000 33.750000) '(143.500000 -77.750000 34.500000)))
(kname ke "Carcass panel")
(ssadd ke ks)
(klay "C-PLINTH")
(setq ke (kbox '(142.750000 -92.000000 0.000000) '(162.000000 -77.000000 4.000000)))
(kname ke "Recessed toe kick")
(ssadd ke ks)
(klay "C-FRONTS")
(setq ke (kbox '(140.750000 -91.937500 4.062500) '(141.500000 -77.062500 34.437500)))
(kname ke "Full-height pullout front")
(ssadd ke ks)
(klay "C-HARDWARE")
(setq ke (kbox '(141.500000 -78.050000 5.790000) '(161.185000 -77.800000 6.490000)))
(kname ke "500mm runner profile")
(ssadd ke ks)
(klay "C-HARDWARE")
(setq ke (kbox '(141.500000 -91.200000 5.790000) '(161.185000 -90.950000 6.490000)))
(kname ke "500mm runner profile")
(ssadd ke ks)
(klay "M-METAL")
(setq ke (kbox '(142.500000 -89.950000 6.790000) '(150.000000 -79.050000 6.910000)))
(kname ke "Garbage bin floor")
(ssadd ke ks)
(klay "M-METAL")
(setq ke (kbox '(142.500000 -89.950000 6.910000) '(142.620000 -79.050000 25.290000)))
(kname ke "Garbage bin end")
(ssadd ke ks)
(klay "M-METAL")
(setq ke (kbox '(149.880000 -89.950000 6.910000) '(150.000000 -79.050000 25.290000)))
(kname ke "Garbage bin end")
(ssadd ke ks)
(klay "M-METAL")
(setq ke (kbox '(142.620000 -79.170000 6.910000) '(149.880000 -79.050000 25.290000)))
(kname ke "Garbage bin side")
(ssadd ke ks)
(klay "M-METAL")
(setq ke (kbox '(142.620000 -89.950000 6.910000) '(149.880000 -89.830000 25.290000)))
(kname ke "Garbage bin side")
(ssadd ke ks)
(klay "M-METAL")
(setq ke (kbox '(142.459990 -89.990010 25.150000) '(142.579990 -79.010000 25.450000)))
(kname ke "Garbage rim end")
(ssadd ke ks)
(klay "M-METAL")
(setq ke (kbox '(149.919990 -89.990010 25.150000) '(150.039990 -79.010000 25.450000)))
(kname ke "Garbage rim end")
(ssadd ke ks)
(klay "M-METAL")
(setq ke (kbox '(142.579990 -79.130000 25.150000) '(149.919990 -79.010000 25.450000)))
(kname ke "Garbage rim side")
(ssadd ke ks)
(klay "M-METAL")
(setq ke (kbox '(142.579990 -89.990010 25.150000) '(149.919990 -89.870010 25.450000)))
(kname ke "Garbage rim side")
(ssadd ke ks)
(klay "M-METAL")
(setq ke (kbox '(150.500000 -89.950000 6.790000) '(158.000000 -79.050000 6.910000)))
(kname ke "Recycling bin floor")
(ssadd ke ks)
(klay "M-METAL")
(setq ke (kbox '(150.500000 -89.950000 6.910000) '(150.620000 -79.050000 25.290000)))
(kname ke "Recycling bin end")
(ssadd ke ks)
(klay "M-METAL")
(setq ke (kbox '(157.880000 -89.950000 6.910000) '(158.000000 -79.050000 25.290000)))
(kname ke "Recycling bin end")
(ssadd ke ks)
(klay "M-METAL")
(setq ke (kbox '(150.620000 -79.170000 6.910000) '(157.880000 -79.050000 25.290000)))
(kname ke "Recycling bin side")
(ssadd ke ks)
(klay "M-METAL")
(setq ke (kbox '(150.620000 -89.950000 6.910000) '(157.880000 -89.830000 25.290000)))
(kname ke "Recycling bin side")
(ssadd ke ks)
(klay "M-METAL")
(setq ke (kbox '(150.460010 -89.990010 25.150000) '(150.580010 -79.010000 25.450000)))
(kname ke "Recycling rim end")
(ssadd ke ks)
(klay "M-METAL")
(setq ke (kbox '(157.919990 -89.990010 25.150000) '(158.039990 -79.010000 25.450000)))
(kname ke "Recycling rim end")
(ssadd ke ks)
(klay "M-METAL")
(setq ke (kbox '(150.580010 -79.130000 25.150000) '(157.919990 -79.010000 25.450000)))
(kname ke "Recycling rim side")
(ssadd ke ks)
(klay "M-METAL")
(setq ke (kbox '(150.580010 -89.990010 25.150000) '(157.919990 -89.870010 25.450000)))
(kname ke "Recycling rim side")
(ssadd ke ks)
(klay "C-HARDWARE")
(setq ke (kbox '(160.291340 -90.423230 6.790000) '(160.791340 -78.576770 9.500000)))
(kname ke "SB04 garbagepullout drawer1 box back")
(ssadd ke ks)
(klay "C-HARDWARE")
(setq ke (kbox '(141.630000 -90.553240 6.290000) '(160.661330 -78.446780 6.790000)))
(kname ke "SB04 garbagepullout drawer1 box bottom")
(ssadd ke ks)
(klay "C-HARDWARE")
(setq ke (kbox '(141.500000 -78.576770 5.790000) '(160.791340 -78.076770 9.500000)))
(kname ke "SB04 garbagepullout drawer1 box side")
(ssadd ke ks)
(klay "C-HARDWARE")
(setq ke (kbox '(141.500000 -90.923230 5.790000) '(160.791340 -90.423230 9.500000)))
(kname ke "SB04 garbagepullout drawer1 box side.001")
(ssadd ke ks)
(klay "C-HARDWARE")
(setq ke (kbox '(141.500000 -90.423230 6.790000) '(142.000000 -78.576770 33.500000)))
(kname ke "SB04 garbagepullout drawer1 box subfront")
(ssadd ke ks)
(klay "C-HARDWARE")
(setq ke (kbox '(139.765750 -87.177170 32.962210) '(139.985750 -81.822840 33.237800)))
(kname ke "Top horizontal nickel pull")
(ssadd ke ks)
(klay "C-HARDWARE")
(setq ke (kbox '(139.765750 -82.935230 32.880000) '(140.750000 -82.285230 33.320000)))
(kname ke "Pull fixing")
(ssadd ke ks)
(klay "C-HARDWARE")
(setq ke (kbox '(139.765750 -86.714760 32.880000) '(140.750000 -86.064760 33.320000)))
(kname ke "Pull fixing")
(ssadd ke ks)
(klay "C-HARDWARE")
(setq ke (kbox '(142.200000 -79.000000 25.450000) '(158.300000 -78.750010 25.700000)))
(kname ke "Waste bin lateral retaining bar")
(ssadd ke ks)
(klay "C-HARDWARE")
(setq ke (kbox '(142.200000 -90.250000 25.450000) '(158.300000 -90.000000 25.700000)))
(kname ke "Waste bin lateral retaining bar.001")
(ssadd ke ks)
(klay "C-HARDWARE")
(setq ke (kbox '(149.899990 -79.750000 6.790000) '(150.600010 -79.200000 7.100000)))
(kname ke "Waste divider floor angle bracket")
(ssadd ke ks)
(klay "C-HARDWARE")
(setq ke (kbox '(149.899990 -89.750000 6.790000) '(150.600010 -89.200000 7.100000)))
(kname ke "Waste divider floor angle bracket.001")
(ssadd ke ks)
(klay "C-HARDWARE")
(setq ke (kbox '(142.200000 -79.000000 6.790000) '(142.450000 -78.750010 25.450000)))
(kname ke "Waste retaining bar base post")
(ssadd ke ks)
(klay "C-HARDWARE")
(setq ke (kbox '(158.050000 -79.000000 6.790000) '(158.300000 -78.750010 25.450000)))
(kname ke "Waste retaining bar base post.001")
(ssadd ke ks)
(klay "C-HARDWARE")
(setq ke (kbox '(142.200000 -90.250000 6.790000) '(142.450000 -90.000000 25.450000)))
(kname ke "Waste retaining bar base post.002")
(ssadd ke ks)
(klay "C-HARDWARE")
(setq ke (kbox '(158.050000 -90.250000 6.790000) '(158.300000 -90.000000 25.450000)))
(kname ke "Waste retaining bar base post.003")
(ssadd ke ks)
(klay "C-CARCASS")
(setq ke (kbox '(150.130000 -90.250000 6.790000) '(150.370000 -78.750010 25.150000)))
(kname ke "Waste tandem internal divider")
(ssadd ke ks)
(klay "0") (command "_.-BLOCK" "PULLOUT-WASTE" '(0 0 0) ks "")
(klay "0") (command "_.-INSERT" "PULLOUT-WASTE" '(0 0 0) 1 1 0)
(setq ks (ssadd))
(klay "C-CARCASS")
(setq ke (kbox '(141.500000 -141.500000 4.000000) '(165.000000 -140.750000 34.500000)))
(kname ke "Carcass panel")
(ssadd ke ks)
(klay "C-CARCASS")
(setq ke (kbox '(141.500000 -161.750000 4.000000) '(165.000000 -161.000000 34.500000)))
(kname ke "Carcass panel")
(ssadd ke ks)
(klay "C-CARCASS")
(setq ke (kbox '(141.500000 -161.000000 4.000000) '(165.000000 -141.500000 4.750000)))
(kname ke "Carcass panel")
(ssadd ke ks)
(klay "C-CARCASS")
(setq ke (kbox '(164.500000 -161.000000 4.750000) '(165.000000 -141.500000 34.500000)))
(kname ke "Carcass panel")
(ssadd ke ks)
(klay "C-CARCASS")
(setq ke (kbox '(163.000000 -161.000000 33.750000) '(165.000000 -141.500000 34.500000)))
(kname ke "Carcass panel")
(ssadd ke ks)
(klay "C-CARCASS")
(setq ke (kbox '(141.500000 -161.000000 33.750000) '(143.500000 -141.500000 34.500000)))
(kname ke "Carcass panel")
(ssadd ke ks)
(klay "C-PLINTH")
(setq ke (kbox '(142.750000 -161.750000 0.000000) '(162.000000 -140.750000 4.000000)))
(kname ke "Recessed toe kick")
(ssadd ke ks)
(klay "C-FRONTS")
(setq ke (kbox '(140.750000 -161.687500 4.062500) '(141.500000 -140.812500 15.937500)))
(kname ke "Drawer front")
(ssadd ke ks)
(klay "C-CARCASS")
(setq ke (kbox '(141.750000 -160.250000 5.250000) '(163.000000 -142.250000 5.750000)))
(kname ke "Drawer floor")
(ssadd ke ks)
(klay "C-CARCASS")
(setq ke (kbox '(141.750000 -142.250000 5.250000) '(163.000000 -141.750000 12.250000)))
(kname ke "Drawer box")
(ssadd ke ks)
(klay "C-CARCASS")
(setq ke (kbox '(141.750000 -160.750000 5.250000) '(163.000000 -160.250000 12.250000)))
(kname ke "Drawer box")
(ssadd ke ks)
(klay "C-CARCASS")
(setq ke (kbox '(162.500000 -160.250000 5.750000) '(163.000000 -142.250000 12.250000)))
(kname ke "Drawer box")
(ssadd ke ks)
(klay "C-CARCASS")
(setq ke (kbox '(141.750000 -160.250000 5.750000) '(142.250000 -142.250000 12.250000)))
(kname ke "Drawer box")
(ssadd ke ks)
(klay "C-HARDWARE")
(setq ke (kbox '(141.750000 -141.750000 4.950000) '(163.000000 -141.550000 5.650000)))
(kname ke "Runner profile")
(ssadd ke ks)
(klay "C-HARDWARE")
(setq ke (kbox '(141.750000 -160.950000 4.950000) '(163.000000 -160.750000 5.650000)))
(kname ke "Runner profile")
(ssadd ke ks)
(klay "C-HARDWARE")
(setq ke (kbox '(139.765748 -153.927165 12.860000) '(140.200000 -148.572835 13.140000)))
(kname ke "Nickel pull")
(ssadd ke ks)
(klay "C-HARDWARE")
(setq ke (kbox '(140.150000 -149.500236 12.860000) '(140.750000 -149.220236 13.140000)))
(kname ke "Pull fixing")
(ssadd ke ks)
(klay "C-HARDWARE")
(setq ke (kbox '(140.150000 -153.279764 12.860000) '(140.750000 -152.999764 13.140000)))
(kname ke "Pull fixing")
(ssadd ke ks)
(klay "C-FRONTS")
(setq ke (kbox '(140.750000 -161.687500 16.062500) '(141.500000 -140.812500 22.937500)))
(kname ke "Drawer front")
(ssadd ke ks)
(klay "C-CARCASS")
(setq ke (kbox '(141.750000 -160.250000 17.250000) '(163.000000 -142.250000 17.750000)))
(kname ke "Drawer floor")
(ssadd ke ks)
(klay "C-CARCASS")
(setq ke (kbox '(141.750000 -142.250000 17.250000) '(163.000000 -141.750000 21.750000)))
(kname ke "Drawer box")
(ssadd ke ks)
(klay "C-CARCASS")
(setq ke (kbox '(141.750000 -160.750000 17.250000) '(163.000000 -160.250000 21.750000)))
(kname ke "Drawer box")
(ssadd ke ks)
(klay "C-CARCASS")
(setq ke (kbox '(162.500000 -160.250000 17.750000) '(163.000000 -142.250000 21.750000)))
(kname ke "Drawer box")
(ssadd ke ks)
(klay "C-CARCASS")
(setq ke (kbox '(141.750000 -160.250000 17.750000) '(142.250000 -142.250000 21.750000)))
(kname ke "Drawer box")
(ssadd ke ks)
(klay "C-HARDWARE")
(setq ke (kbox '(141.750000 -141.750000 16.950000) '(163.000000 -141.550000 17.650000)))
(kname ke "Runner profile")
(ssadd ke ks)
(klay "C-HARDWARE")
(setq ke (kbox '(141.750000 -160.950000 16.950000) '(163.000000 -160.750000 17.650000)))
(kname ke "Runner profile")
(ssadd ke ks)
(klay "C-HARDWARE")
(setq ke (kbox '(139.765748 -153.927165 19.860000) '(140.200000 -148.572835 20.140000)))
(kname ke "Nickel pull")
(ssadd ke ks)
(klay "C-HARDWARE")
(setq ke (kbox '(140.150000 -149.500236 19.860000) '(140.750000 -149.220236 20.140000)))
(kname ke "Pull fixing")
(ssadd ke ks)
(klay "C-HARDWARE")
(setq ke (kbox '(140.150000 -153.279764 19.860000) '(140.750000 -152.999764 20.140000)))
(kname ke "Pull fixing")
(ssadd ke ks)
(klay "C-FRONTS")
(setq ke (kbox '(140.750000 -161.687500 23.062500) '(141.500000 -140.812500 34.437500)))
(kname ke "Drawer front")
(ssadd ke ks)
(klay "C-CARCASS")
(setq ke (kbox '(141.750000 -160.250000 24.250000) '(163.000000 -142.250000 24.750000)))
(kname ke "Drawer floor")
(ssadd ke ks)
(klay "C-CARCASS")
(setq ke (kbox '(141.750000 -142.250000 24.250000) '(163.000000 -141.750000 31.250000)))
(kname ke "Drawer box")
(ssadd ke ks)
(klay "C-CARCASS")
(setq ke (kbox '(141.750000 -160.750000 24.250000) '(163.000000 -160.250000 31.250000)))
(kname ke "Drawer box")
(ssadd ke ks)
(klay "C-CARCASS")
(setq ke (kbox '(162.500000 -160.250000 24.750000) '(163.000000 -142.250000 31.250000)))
(kname ke "Drawer box")
(ssadd ke ks)
(klay "C-CARCASS")
(setq ke (kbox '(141.750000 -160.250000 24.750000) '(142.250000 -142.250000 31.250000)))
(kname ke "Drawer box")
(ssadd ke ks)
(klay "C-HARDWARE")
(setq ke (kbox '(141.750000 -141.750000 23.950000) '(163.000000 -141.550000 24.650000)))
(kname ke "Runner profile")
(ssadd ke ks)
(klay "C-HARDWARE")
(setq ke (kbox '(141.750000 -160.950000 23.950000) '(163.000000 -160.750000 24.650000)))
(kname ke "Runner profile")
(ssadd ke ks)
(klay "C-HARDWARE")
(setq ke (kbox '(139.765748 -153.927165 31.360000) '(140.200000 -148.572835 31.640000)))
(kname ke "Nickel pull")
(ssadd ke ks)
(klay "C-HARDWARE")
(setq ke (kbox '(140.150000 -149.500236 31.360000) '(140.750000 -149.220236 31.640000)))
(kname ke "Pull fixing")
(ssadd ke ks)
(klay "C-HARDWARE")
(setq ke (kbox '(140.150000 -153.279764 31.360000) '(140.750000 -152.999764 31.640000)))
(kname ke "Pull fixing")
(ssadd ke ks)
(klay "0") (command "_.-BLOCK" "S-140.75" '(0 0 0) ks "")
(klay "0") (command "_.-INSERT" "S-140.75" '(0 0 0) 1 1 0)
(setq ks (ssadd))
(klay "C-FRONTS")
(setq ke (kbox '(139.500000 -116.750000 0.000000) '(165.000000 -116.000000 34.500000)))
(kname ke "Wine divider")
(ssadd ke ks)
(klay "C-FRONTS")
(setq ke (kbox '(139.500000 -162.500000 0.000000) '(165.000000 -161.750000 34.500000)))
(kname ke "Sink end panel")
(ssadd ke ks)
(klay "0") (command "_.-BLOCK" "S-PANELS" '(0 0 0) ks "")
(klay "0") (command "_.-INSERT" "S-PANELS" '(0 0 0) 1 1 0)
(setq ks (ssadd))
(klay "C-CARCASS")
(setq ke (kbox '(0.000000 -13.250000 56.000000) '(0.750000 0.000000 106.000000)))
(kname ke "Carcass panel")
(ssadd ke ks)
(klay "C-CARCASS")
(setq ke (kbox '(16.500000 -13.250000 56.000000) '(17.250000 0.000000 106.000000)))
(kname ke "Carcass panel")
(ssadd ke ks)
(klay "C-CARCASS")
(setq ke (kbox '(0.750000 -13.250000 56.000000) '(16.500000 0.000000 56.750000)))
(kname ke "Carcass panel")
(ssadd ke ks)
(klay "C-CARCASS")
(setq ke (kbox '(0.750000 -0.500000 56.750000) '(16.500000 0.000000 106.000000)))
(kname ke "Carcass panel")
(ssadd ke ks)
(klay "C-CARCASS")
(setq ke (kbox '(0.750000 -2.000000 105.250000) '(16.500000 0.000000 106.000000)))
(kname ke "Carcass panel")
(ssadd ke ks)
(klay "C-CARCASS")
(setq ke (kbox '(0.750000 -13.250000 105.250000) '(16.500000 -11.250000 106.000000)))
(kname ke "Carcass panel")
(ssadd ke ks)
(klay "C-FRONTS")
(setq ke (kbox '(0.062500 -14.000000 56.062500) '(17.187500 -13.250000 105.937500)))
(kname ke "Door front")
(ssadd ke ks)
(klay "C-HARDWARE")
(setq ke (kbox '(15.110000 -14.984252 78.322835) '(15.390000 -14.550000 83.677165)))
(kname ke "Nickel pull")
(ssadd ke ks)
(klay "C-HARDWARE")
(setq ke (kbox '(15.110000 -14.600000 78.970236) '(15.390000 -14.000000 79.250236)))
(kname ke "Pull fixing")
(ssadd ke ks)
(klay "C-HARDWARE")
(setq ke (kbox '(15.110000 -14.600000 82.749764) '(15.390000 -14.000000 83.029764)))
(kname ke "Pull fixing")
(ssadd ke ks)
(klay "C-HARDWARE")
(setq ke (kbox '(0.750000 -13.250000 60.200000) '(2.250000 -12.000000 61.800000)))
(kname ke "Concealed hinge")
(ssadd ke ks)
(klay "C-HARDWARE")
(setq ke (kbox '(0.750000 -13.250000 100.200000) '(2.250000 -12.000000 101.800000)))
(kname ke "Concealed hinge")
(ssadd ke ks)
(klay "C-CARCASS")
(setq ke (kbox '(0.750000 -13.000000 72.666667) '(16.500000 -0.500000 73.416667)))
(kname ke "Fixed shelf")
(ssadd ke ks)
(klay "C-CARCASS")
(setq ke (kbox '(0.750000 -13.000000 89.333333) '(16.500000 -0.500000 90.083333)))
(kname ke "Fixed shelf")
(ssadd ke ks)
(klay "0") (command "_.-BLOCK" "U-B-0" '(0 0 0) ks "")
(klay "0") (command "_.-INSERT" "U-B-0" '(0 0 0) 1 1 0)
(setq ks (ssadd))
(klay "C-CARCASS")
(setq ke (kbox '(17.250000 -13.250000 56.000000) '(18.000000 0.000000 106.000000)))
(kname ke "Carcass panel")
(ssadd ke ks)
(klay "C-CARCASS")
(setq ke (kbox '(49.750000 -13.250000 56.000000) '(50.500000 0.000000 106.000000)))
(kname ke "Carcass panel")
(ssadd ke ks)
(klay "C-CARCASS")
(setq ke (kbox '(18.000000 -13.250000 56.000000) '(49.750000 0.000000 56.750000)))
(kname ke "Carcass panel")
(ssadd ke ks)
(klay "C-CARCASS")
(setq ke (kbox '(18.000000 -0.500000 56.750000) '(49.750000 0.000000 106.000000)))
(kname ke "Carcass panel")
(ssadd ke ks)
(klay "C-CARCASS")
(setq ke (kbox '(18.000000 -2.000000 105.250000) '(49.750000 0.000000 106.000000)))
(kname ke "Carcass panel")
(ssadd ke ks)
(klay "C-CARCASS")
(setq ke (kbox '(18.000000 -13.250000 105.250000) '(49.750000 -11.250000 106.000000)))
(kname ke "Carcass panel")
(ssadd ke ks)
(klay "C-FRONTS")
(setq ke (kbox '(17.312500 -14.000000 56.062500) '(33.812500 -13.250000 105.937500)))
(kname ke "Door front")
(ssadd ke ks)
(klay "C-HARDWARE")
(setq ke (kbox '(31.735000 -14.984252 78.322835) '(32.015000 -14.550000 83.677165)))
(kname ke "Nickel pull")
(ssadd ke ks)
(klay "C-HARDWARE")
(setq ke (kbox '(31.735000 -14.600000 78.970236) '(32.015000 -14.000000 79.250236)))
(kname ke "Pull fixing")
(ssadd ke ks)
(klay "C-HARDWARE")
(setq ke (kbox '(31.735000 -14.600000 82.749764) '(32.015000 -14.000000 83.029764)))
(kname ke "Pull fixing")
(ssadd ke ks)
(klay "C-HARDWARE")
(setq ke (kbox '(18.000000 -13.250000 60.200000) '(19.500000 -12.000000 61.800000)))
(kname ke "Concealed hinge")
(ssadd ke ks)
(klay "C-HARDWARE")
(setq ke (kbox '(18.000000 -13.250000 100.200000) '(19.500000 -12.000000 101.800000)))
(kname ke "Concealed hinge")
(ssadd ke ks)
(klay "C-FRONTS")
(setq ke (kbox '(33.937500 -14.000000 56.062500) '(50.437500 -13.250000 105.937500)))
(kname ke "Door front")
(ssadd ke ks)
(klay "C-HARDWARE")
(setq ke (kbox '(35.735000 -14.984252 78.322835) '(36.015000 -14.550000 83.677165)))
(kname ke "Nickel pull")
(ssadd ke ks)
(klay "C-HARDWARE")
(setq ke (kbox '(35.735000 -14.600000 78.970236) '(36.015000 -14.000000 79.250236)))
(kname ke "Pull fixing")
(ssadd ke ks)
(klay "C-HARDWARE")
(setq ke (kbox '(35.735000 -14.600000 82.749764) '(36.015000 -14.000000 83.029764)))
(kname ke "Pull fixing")
(ssadd ke ks)
(klay "C-HARDWARE")
(setq ke (kbox '(34.625000 -13.250000 60.200000) '(36.125000 -12.000000 61.800000)))
(kname ke "Concealed hinge")
(ssadd ke ks)
(klay "C-HARDWARE")
(setq ke (kbox '(34.625000 -13.250000 100.200000) '(36.125000 -12.000000 101.800000)))
(kname ke "Concealed hinge")
(ssadd ke ks)
(klay "C-CARCASS")
(setq ke (kbox '(18.000000 -13.000000 72.666667) '(49.750000 -0.500000 73.416667)))
(kname ke "Fixed shelf")
(ssadd ke ks)
(klay "C-CARCASS")
(setq ke (kbox '(18.000000 -13.000000 89.333333) '(49.750000 -0.500000 90.083333)))
(kname ke "Fixed shelf")
(ssadd ke ks)
(klay "0") (command "_.-BLOCK" "U-B-17.25" '(0 0 0) ks "")
(klay "0") (command "_.-INSERT" "U-B-17.25" '(0 0 0) 1 1 0)
(setq ks (ssadd))
(klay "C-CARCASS")
(setq ke (kbox '(116.500000 -13.250000 56.000000) '(117.250000 0.000000 106.000000)))
(kname ke "Carcass panel")
(ssadd ke ks)
(klay "C-CARCASS")
(setq ke (kbox '(147.000000 -13.250000 56.000000) '(147.750000 0.000000 106.000000)))
(kname ke "Carcass panel")
(ssadd ke ks)
(klay "C-CARCASS")
(setq ke (kbox '(117.250000 -13.250000 56.000000) '(147.000000 0.000000 56.750000)))
(kname ke "Carcass panel")
(ssadd ke ks)
(klay "C-CARCASS")
(setq ke (kbox '(117.250000 -0.500000 56.750000) '(147.000000 0.000000 106.000000)))
(kname ke "Carcass panel")
(ssadd ke ks)
(klay "C-CARCASS")
(setq ke (kbox '(117.250000 -2.000000 105.250000) '(147.000000 0.000000 106.000000)))
(kname ke "Carcass panel")
(ssadd ke ks)
(klay "C-CARCASS")
(setq ke (kbox '(117.250000 -13.250000 105.250000) '(147.000000 -11.250000 106.000000)))
(kname ke "Carcass panel")
(ssadd ke ks)
(klay "C-FRONTS")
(setq ke (kbox '(116.562500 -14.000000 56.062500) '(132.062500 -13.250000 105.937500)))
(kname ke "Door front")
(ssadd ke ks)
(klay "C-HARDWARE")
(setq ke (kbox '(129.985000 -14.984252 78.322835) '(130.265000 -14.550000 83.677165)))
(kname ke "Nickel pull")
(ssadd ke ks)
(klay "C-HARDWARE")
(setq ke (kbox '(129.985000 -14.600000 78.970236) '(130.265000 -14.000000 79.250236)))
(kname ke "Pull fixing")
(ssadd ke ks)
(klay "C-HARDWARE")
(setq ke (kbox '(129.985000 -14.600000 82.749764) '(130.265000 -14.000000 83.029764)))
(kname ke "Pull fixing")
(ssadd ke ks)
(klay "C-HARDWARE")
(setq ke (kbox '(117.250000 -13.250000 60.200000) '(118.750000 -12.000000 61.800000)))
(kname ke "Concealed hinge")
(ssadd ke ks)
(klay "C-HARDWARE")
(setq ke (kbox '(117.250000 -13.250000 100.200000) '(118.750000 -12.000000 101.800000)))
(kname ke "Concealed hinge")
(ssadd ke ks)
(klay "C-FRONTS")
(setq ke (kbox '(132.187500 -14.000000 56.062500) '(147.687500 -13.250000 105.937500)))
(kname ke "Door front")
(ssadd ke ks)
(klay "C-HARDWARE")
(setq ke (kbox '(133.985000 -14.984252 78.322835) '(134.265000 -14.550000 83.677165)))
(kname ke "Nickel pull")
(ssadd ke ks)
(klay "C-HARDWARE")
(setq ke (kbox '(133.985000 -14.600000 78.970236) '(134.265000 -14.000000 79.250236)))
(kname ke "Pull fixing")
(ssadd ke ks)
(klay "C-HARDWARE")
(setq ke (kbox '(133.985000 -14.600000 82.749764) '(134.265000 -14.000000 83.029764)))
(kname ke "Pull fixing")
(ssadd ke ks)
(klay "C-HARDWARE")
(setq ke (kbox '(132.875000 -13.250000 60.200000) '(134.375000 -12.000000 61.800000)))
(kname ke "Concealed hinge")
(ssadd ke ks)
(klay "C-HARDWARE")
(setq ke (kbox '(132.875000 -13.250000 100.200000) '(134.375000 -12.000000 101.800000)))
(kname ke "Concealed hinge")
(ssadd ke ks)
(klay "C-CARCASS")
(setq ke (kbox '(117.250000 -13.000000 72.666667) '(147.000000 -0.500000 73.416667)))
(kname ke "Fixed shelf")
(ssadd ke ks)
(klay "C-CARCASS")
(setq ke (kbox '(117.250000 -13.000000 89.333333) '(147.000000 -0.500000 90.083333)))
(kname ke "Fixed shelf")
(ssadd ke ks)
(klay "0") (command "_.-BLOCK" "U-B-116.5" '(0 0 0) ks "")
(klay "0") (command "_.-INSERT" "U-B-116.5" '(0 0 0) 1 1 0)
(setq ks (ssadd))
(klay "C-CARCASS")
(setq ke (kbox '(147.750000 -13.250000 56.000000) '(148.500000 0.000000 106.000000)))
(kname ke "Carcass panel")
(ssadd ke ks)
(klay "C-CARCASS")
(setq ke (kbox '(164.250000 -13.250000 56.000000) '(165.000000 0.000000 106.000000)))
(kname ke "Carcass panel")
(ssadd ke ks)
(klay "C-CARCASS")
(setq ke (kbox '(148.500000 -13.250000 56.000000) '(164.250000 0.000000 56.750000)))
(kname ke "Carcass panel")
(ssadd ke ks)
(klay "C-CARCASS")
(setq ke (kbox '(148.500000 -0.500000 56.750000) '(164.250000 0.000000 106.000000)))
(kname ke "Carcass panel")
(ssadd ke ks)
(klay "C-CARCASS")
(setq ke (kbox '(148.500000 -2.000000 105.250000) '(164.250000 0.000000 106.000000)))
(kname ke "Carcass panel")
(ssadd ke ks)
(klay "C-CARCASS")
(setq ke (kbox '(148.500000 -13.250000 105.250000) '(164.250000 -11.250000 106.000000)))
(kname ke "Carcass panel")
(ssadd ke ks)
(klay "C-FRONTS")
(setq ke (kbox '(147.812500 -14.000000 56.062500) '(164.937500 -13.250000 105.937500)))
(kname ke "Door front")
(ssadd ke ks)
(klay "C-HARDWARE")
(setq ke (kbox '(162.860000 -14.984252 78.322835) '(163.140000 -14.550000 83.677165)))
(kname ke "Nickel pull")
(ssadd ke ks)
(klay "C-HARDWARE")
(setq ke (kbox '(162.860000 -14.600000 78.970236) '(163.140000 -14.000000 79.250236)))
(kname ke "Pull fixing")
(ssadd ke ks)
(klay "C-HARDWARE")
(setq ke (kbox '(162.860000 -14.600000 82.749764) '(163.140000 -14.000000 83.029764)))
(kname ke "Pull fixing")
(ssadd ke ks)
(klay "C-HARDWARE")
(setq ke (kbox '(148.500000 -13.250000 60.200000) '(150.000000 -12.000000 61.800000)))
(kname ke "Concealed hinge")
(ssadd ke ks)
(klay "C-HARDWARE")
(setq ke (kbox '(148.500000 -13.250000 100.200000) '(150.000000 -12.000000 101.800000)))
(kname ke "Concealed hinge")
(ssadd ke ks)
(klay "C-CARCASS")
(setq ke (kbox '(148.500000 -13.000000 72.666667) '(164.250000 -0.500000 73.416667)))
(kname ke "Fixed shelf")
(ssadd ke ks)
(klay "C-CARCASS")
(setq ke (kbox '(148.500000 -13.000000 89.333333) '(164.250000 -0.500000 90.083333)))
(kname ke "Fixed shelf")
(ssadd ke ks)
(klay "0") (command "_.-BLOCK" "U-B-147.75" '(0 0 0) ks "")
(klay "0") (command "_.-INSERT" "U-B-147.75" '(0 0 0) 1 1 0)
(setq ks (ssadd))
(klay "C-CARCASS")
(setq ke (kbox '(0.000000 -0.750000 56.000000) '(13.250000 0.000000 106.000000)))
(kname ke "Carcass panel")
(ssadd ke ks)
(klay "C-CARCASS")
(setq ke (kbox '(0.000000 -18.750000 56.000000) '(13.250000 -18.000000 106.000000)))
(kname ke "Carcass panel")
(ssadd ke ks)
(klay "C-CARCASS")
(setq ke (kbox '(0.000000 -18.000000 56.000000) '(13.250000 -0.750000 56.750000)))
(kname ke "Carcass panel")
(ssadd ke ks)
(klay "C-CARCASS")
(setq ke (kbox '(0.000000 -18.000000 56.750000) '(0.500000 -0.750000 106.000000)))
(kname ke "Carcass panel")
(ssadd ke ks)
(klay "C-CARCASS")
(setq ke (kbox '(0.000000 -18.000000 105.250000) '(2.000000 -0.750000 106.000000)))
(kname ke "Carcass panel")
(ssadd ke ks)
(klay "C-CARCASS")
(setq ke (kbox '(11.250000 -18.000000 105.250000) '(13.250000 -0.750000 106.000000)))
(kname ke "Carcass panel")
(ssadd ke ks)
(klay "C-FRONTS")
(setq ke (kbox '(13.250000 -18.687500 56.062500) '(14.000000 -0.062500 105.937500)))
(kname ke "Door front")
(ssadd ke ks)
(klay "C-HARDWARE")
(setq ke (kbox '(14.550000 -16.890000 78.322835) '(14.984252 -16.610000 83.677165)))
(kname ke "Nickel pull")
(ssadd ke ks)
(klay "C-HARDWARE")
(setq ke (kbox '(14.000000 -16.890000 78.970236) '(14.600000 -16.610000 79.250236)))
(kname ke "Pull fixing")
(ssadd ke ks)
(klay "C-HARDWARE")
(setq ke (kbox '(14.000000 -16.890000 82.749764) '(14.600000 -16.610000 83.029764)))
(kname ke "Pull fixing")
(ssadd ke ks)
(klay "C-HARDWARE")
(setq ke (kbox '(12.000000 -2.250000 60.200000) '(13.250000 -0.750000 61.800000)))
(kname ke "Concealed hinge")
(ssadd ke ks)
(klay "C-HARDWARE")
(setq ke (kbox '(12.000000 -2.250000 100.200000) '(13.250000 -0.750000 101.800000)))
(kname ke "Concealed hinge")
(ssadd ke ks)
(klay "C-CARCASS")
(setq ke (kbox '(0.500000 -18.000000 72.666667) '(13.000000 -0.750000 73.416667)))
(kname ke "Fixed shelf")
(ssadd ke ks)
(klay "C-CARCASS")
(setq ke (kbox '(0.500000 -18.000000 89.333333) '(13.000000 -0.750000 90.083333)))
(kname ke "Fixed shelf")
(ssadd ke ks)
(klay "0") (command "_.-BLOCK" "U-L-0" '(0 0 0) ks "")
(klay "0") (command "_.-INSERT" "U-L-0" '(0 0 0) 1 1 0)
(setq ks (ssadd))
(klay "C-CARCASS")
(setq ke (kbox '(0.000000 -19.500000 56.000000) '(13.250000 -18.750000 106.000000)))
(kname ke "Carcass panel")
(ssadd ke ks)
(klay "C-CARCASS")
(setq ke (kbox '(0.000000 -35.250000 56.000000) '(13.250000 -34.500000 106.000000)))
(kname ke "Carcass panel")
(ssadd ke ks)
(klay "C-CARCASS")
(setq ke (kbox '(0.000000 -34.500000 56.000000) '(13.250000 -19.500000 56.750000)))
(kname ke "Carcass panel")
(ssadd ke ks)
(klay "C-CARCASS")
(setq ke (kbox '(0.000000 -34.500000 56.750000) '(0.500000 -19.500000 106.000000)))
(kname ke "Carcass panel")
(ssadd ke ks)
(klay "C-CARCASS")
(setq ke (kbox '(0.000000 -34.500000 105.250000) '(2.000000 -19.500000 106.000000)))
(kname ke "Carcass panel")
(ssadd ke ks)
(klay "C-CARCASS")
(setq ke (kbox '(11.250000 -34.500000 105.250000) '(13.250000 -19.500000 106.000000)))
(kname ke "Carcass panel")
(ssadd ke ks)
(klay "C-FRONTS")
(setq ke (kbox '(13.250000 -35.187500 56.062500) '(14.000000 -18.812500 105.937500)))
(kname ke "Door front")
(ssadd ke ks)
(klay "C-HARDWARE")
(setq ke (kbox '(14.550000 -33.390000 78.322835) '(14.984252 -33.110000 83.677165)))
(kname ke "Nickel pull")
(ssadd ke ks)
(klay "C-HARDWARE")
(setq ke (kbox '(14.000000 -33.390000 78.970236) '(14.600000 -33.110000 79.250236)))
(kname ke "Pull fixing")
(ssadd ke ks)
(klay "C-HARDWARE")
(setq ke (kbox '(14.000000 -33.390000 82.749764) '(14.600000 -33.110000 83.029764)))
(kname ke "Pull fixing")
(ssadd ke ks)
(klay "C-HARDWARE")
(setq ke (kbox '(12.000000 -21.000000 60.200000) '(13.250000 -19.500000 61.800000)))
(kname ke "Concealed hinge")
(ssadd ke ks)
(klay "C-HARDWARE")
(setq ke (kbox '(12.000000 -21.000000 100.200000) '(13.250000 -19.500000 101.800000)))
(kname ke "Concealed hinge")
(ssadd ke ks)
(klay "C-CARCASS")
(setq ke (kbox '(0.500000 -34.500000 72.666667) '(13.000000 -19.500000 73.416667)))
(kname ke "Fixed shelf")
(ssadd ke ks)
(klay "C-CARCASS")
(setq ke (kbox '(0.500000 -34.500000 89.333333) '(13.000000 -19.500000 90.083333)))
(kname ke "Fixed shelf")
(ssadd ke ks)
(klay "0") (command "_.-BLOCK" "U-L-18.75" '(0 0 0) ks "")
(klay "0") (command "_.-INSERT" "U-L-18.75" '(0 0 0) 1 1 0)
(setq ks (ssadd))
(klay "C-CARCASS")
(setq ke (kbox '(151.750000 -0.750000 56.000000) '(165.000000 0.000000 106.000000)))
(kname ke "Carcass panel")
(ssadd ke ks)
(klay "C-CARCASS")
(setq ke (kbox '(151.750000 -16.500000 56.000000) '(165.000000 -15.750000 106.000000)))
(kname ke "Carcass panel")
(ssadd ke ks)
(klay "C-CARCASS")
(setq ke (kbox '(151.750000 -15.750000 56.000000) '(165.000000 -0.750000 56.750000)))
(kname ke "Carcass panel")
(ssadd ke ks)
(klay "C-CARCASS")
(setq ke (kbox '(164.500000 -15.750000 56.750000) '(165.000000 -0.750000 106.000000)))
(kname ke "Carcass panel")
(ssadd ke ks)
(klay "C-CARCASS")
(setq ke (kbox '(163.000000 -15.750000 105.250000) '(165.000000 -0.750000 106.000000)))
(kname ke "Carcass panel")
(ssadd ke ks)
(klay "C-CARCASS")
(setq ke (kbox '(151.750000 -15.750000 105.250000) '(153.750000 -0.750000 106.000000)))
(kname ke "Carcass panel")
(ssadd ke ks)
(klay "C-FRONTS")
(setq ke (kbox '(151.000000 -16.437500 56.062500) '(151.750000 -0.062500 105.937500)))
(kname ke "Door front")
(ssadd ke ks)
(klay "C-HARDWARE")
(setq ke (kbox '(150.015748 -14.640000 78.322835) '(150.450000 -14.360000 83.677165)))
(kname ke "Nickel pull")
(ssadd ke ks)
(klay "C-HARDWARE")
(setq ke (kbox '(150.400000 -14.640000 78.970236) '(151.000000 -14.360000 79.250236)))
(kname ke "Pull fixing")
(ssadd ke ks)
(klay "C-HARDWARE")
(setq ke (kbox '(150.400000 -14.640000 82.749764) '(151.000000 -14.360000 83.029764)))
(kname ke "Pull fixing")
(ssadd ke ks)
(klay "C-HARDWARE")
(setq ke (kbox '(151.750000 -2.250000 60.200000) '(153.000000 -0.750000 61.800000)))
(kname ke "Concealed hinge")
(ssadd ke ks)
(klay "C-HARDWARE")
(setq ke (kbox '(151.750000 -2.250000 100.200000) '(153.000000 -0.750000 101.800000)))
(kname ke "Concealed hinge")
(ssadd ke ks)
(klay "C-CARCASS")
(setq ke (kbox '(152.000000 -15.750000 72.666667) '(164.500000 -0.750000 73.416667)))
(kname ke "Fixed shelf")
(ssadd ke ks)
(klay "C-CARCASS")
(setq ke (kbox '(152.000000 -15.750000 89.333333) '(164.500000 -0.750000 90.083333)))
(kname ke "Fixed shelf")
(ssadd ke ks)
(klay "0") (command "_.-BLOCK" "U-S-0" '(0 0 0) ks "")
(klay "0") (command "_.-INSERT" "U-S-0" '(0 0 0) 1 1 0)
(setq ks (ssadd))
(klay "C-CARCASS")
(setq ke (kbox '(151.750000 -17.250000 56.000000) '(165.000000 -16.500000 106.000000)))
(kname ke "Carcass panel")
(ssadd ke ks)
(klay "C-CARCASS")
(setq ke (kbox '(151.750000 -32.250000 56.000000) '(165.000000 -31.500000 106.000000)))
(kname ke "Carcass panel")
(ssadd ke ks)
(klay "C-CARCASS")
(setq ke (kbox '(151.750000 -31.500000 56.000000) '(165.000000 -17.250000 56.750000)))
(kname ke "Carcass panel")
(ssadd ke ks)
(klay "C-CARCASS")
(setq ke (kbox '(164.500000 -31.500000 56.750000) '(165.000000 -17.250000 106.000000)))
(kname ke "Carcass panel")
(ssadd ke ks)
(klay "C-CARCASS")
(setq ke (kbox '(163.000000 -31.500000 105.250000) '(165.000000 -17.250000 106.000000)))
(kname ke "Carcass panel")
(ssadd ke ks)
(klay "C-CARCASS")
(setq ke (kbox '(151.750000 -31.500000 105.250000) '(153.750000 -17.250000 106.000000)))
(kname ke "Carcass panel")
(ssadd ke ks)
(klay "C-FRONTS")
(setq ke (kbox '(151.000000 -32.187500 56.062500) '(151.750000 -16.562500 105.937500)))
(kname ke "Door front")
(ssadd ke ks)
(klay "C-HARDWARE")
(setq ke (kbox '(150.015748 -30.390000 78.322835) '(150.450000 -30.110000 83.677165)))
(kname ke "Nickel pull")
(ssadd ke ks)
(klay "C-HARDWARE")
(setq ke (kbox '(150.400000 -30.390000 78.970236) '(151.000000 -30.110000 79.250236)))
(kname ke "Pull fixing")
(ssadd ke ks)
(klay "C-HARDWARE")
(setq ke (kbox '(150.400000 -30.390000 82.749764) '(151.000000 -30.110000 83.029764)))
(kname ke "Pull fixing")
(ssadd ke ks)
(klay "C-HARDWARE")
(setq ke (kbox '(151.750000 -18.750000 60.200000) '(153.000000 -17.250000 61.800000)))
(kname ke "Concealed hinge")
(ssadd ke ks)
(klay "C-HARDWARE")
(setq ke (kbox '(151.750000 -18.750000 100.200000) '(153.000000 -17.250000 101.800000)))
(kname ke "Concealed hinge")
(ssadd ke ks)
(klay "C-CARCASS")
(setq ke (kbox '(152.000000 -31.500000 72.666667) '(164.500000 -17.250000 73.416667)))
(kname ke "Fixed shelf")
(ssadd ke ks)
(klay "C-CARCASS")
(setq ke (kbox '(152.000000 -31.500000 89.333333) '(164.500000 -17.250000 90.083333)))
(kname ke "Fixed shelf")
(ssadd ke ks)
(klay "0") (command "_.-BLOCK" "U-S-16.5" '(0 0 0) ks "")
(klay "0") (command "_.-INSERT" "U-S-16.5" '(0 0 0) 1 1 0)
(setq ks (ssadd))
(klay "C-CARCASS")
(setq ke (kbox '(151.750000 -87.250000 56.000000) '(165.000000 -86.500000 106.000000)))
(kname ke "Carcass panel")
(ssadd ke ks)
(klay "C-CARCASS")
(setq ke (kbox '(151.750000 -124.625000 56.000000) '(165.000000 -123.875000 106.000000)))
(kname ke "Carcass panel")
(ssadd ke ks)
(klay "C-CARCASS")
(setq ke (kbox '(151.750000 -123.875000 56.000000) '(165.000000 -87.250000 56.750000)))
(kname ke "Carcass panel")
(ssadd ke ks)
(klay "C-CARCASS")
(setq ke (kbox '(164.500000 -123.875000 56.750000) '(165.000000 -87.250000 106.000000)))
(kname ke "Carcass panel")
(ssadd ke ks)
(klay "C-CARCASS")
(setq ke (kbox '(163.000000 -123.875000 105.250000) '(165.000000 -87.250000 106.000000)))
(kname ke "Carcass panel")
(ssadd ke ks)
(klay "C-CARCASS")
(setq ke (kbox '(151.750000 -123.875000 105.250000) '(153.750000 -87.250000 106.000000)))
(kname ke "Carcass panel")
(ssadd ke ks)
(klay "C-FRONTS")
(setq ke (kbox '(151.000000 -105.500000 56.062500) '(151.750000 -86.562500 105.937500)))
(kname ke "Door front")
(ssadd ke ks)
(klay "C-HARDWARE")
(setq ke (kbox '(150.015748 -103.702500 78.322835) '(150.450000 -103.422500 83.677165)))
(kname ke "Nickel pull")
(ssadd ke ks)
(klay "C-HARDWARE")
(setq ke (kbox '(150.400000 -103.702500 78.970236) '(151.000000 -103.422500 79.250236)))
(kname ke "Pull fixing")
(ssadd ke ks)
(klay "C-HARDWARE")
(setq ke (kbox '(150.400000 -103.702500 82.749764) '(151.000000 -103.422500 83.029764)))
(kname ke "Pull fixing")
(ssadd ke ks)
(klay "C-HARDWARE")
(setq ke (kbox '(151.750000 -88.750000 60.200000) '(153.000000 -87.250000 61.800000)))
(kname ke "Concealed hinge")
(ssadd ke ks)
(klay "C-HARDWARE")
(setq ke (kbox '(151.750000 -88.750000 100.200000) '(153.000000 -87.250000 101.800000)))
(kname ke "Concealed hinge")
(ssadd ke ks)
(klay "C-FRONTS")
(setq ke (kbox '(151.000000 -124.562500 56.062500) '(151.750000 -105.625000 105.937500)))
(kname ke "Door front")
(ssadd ke ks)
(klay "C-HARDWARE")
(setq ke (kbox '(150.015748 -107.702500 78.322835) '(150.450000 -107.422500 83.677165)))
(kname ke "Nickel pull")
(ssadd ke ks)
(klay "C-HARDWARE")
(setq ke (kbox '(150.400000 -107.702500 78.970236) '(151.000000 -107.422500 79.250236)))
(kname ke "Pull fixing")
(ssadd ke ks)
(klay "C-HARDWARE")
(setq ke (kbox '(150.400000 -107.702500 82.749764) '(151.000000 -107.422500 83.029764)))
(kname ke "Pull fixing")
(ssadd ke ks)
(klay "C-HARDWARE")
(setq ke (kbox '(151.750000 -107.812500 60.200000) '(153.000000 -106.312500 61.800000)))
(kname ke "Concealed hinge")
(ssadd ke ks)
(klay "C-HARDWARE")
(setq ke (kbox '(151.750000 -107.812500 100.200000) '(153.000000 -106.312500 101.800000)))
(kname ke "Concealed hinge")
(ssadd ke ks)
(klay "C-CARCASS")
(setq ke (kbox '(152.000000 -123.875000 72.666667) '(164.500000 -87.250000 73.416667)))
(kname ke "Fixed shelf")
(ssadd ke ks)
(klay "C-CARCASS")
(setq ke (kbox '(152.000000 -123.875000 89.333333) '(164.500000 -87.250000 90.083333)))
(kname ke "Fixed shelf")
(ssadd ke ks)
(klay "0") (command "_.-BLOCK" "U-S-86.5" '(0 0 0) ks "")
(klay "0") (command "_.-INSERT" "U-S-86.5" '(0 0 0) 1 1 0)
(setq ks (ssadd))
(klay "C-CARCASS")
(setq ke (kbox '(151.750000 -125.375000 56.000000) '(165.000000 -124.625000 106.000000)))
(kname ke "Carcass panel")
(ssadd ke ks)
(klay "C-CARCASS")
(setq ke (kbox '(151.750000 -162.750000 56.000000) '(165.000000 -162.000000 106.000000)))
(kname ke "Carcass panel")
(ssadd ke ks)
(klay "C-CARCASS")
(setq ke (kbox '(151.750000 -162.000000 56.000000) '(165.000000 -125.375000 56.750000)))
(kname ke "Carcass panel")
(ssadd ke ks)
(klay "C-CARCASS")
(setq ke (kbox '(164.500000 -162.000000 56.750000) '(165.000000 -125.375000 106.000000)))
(kname ke "Carcass panel")
(ssadd ke ks)
(klay "C-CARCASS")
(setq ke (kbox '(163.000000 -162.000000 105.250000) '(165.000000 -125.375000 106.000000)))
(kname ke "Carcass panel")
(ssadd ke ks)
(klay "C-CARCASS")
(setq ke (kbox '(151.750000 -162.000000 105.250000) '(153.750000 -125.375000 106.000000)))
(kname ke "Carcass panel")
(ssadd ke ks)
(klay "C-FRONTS")
(setq ke (kbox '(151.000000 -143.625000 56.062500) '(151.750000 -124.687500 105.937500)))
(kname ke "Door front")
(ssadd ke ks)
(klay "C-HARDWARE")
(setq ke (kbox '(150.015748 -141.827500 78.322835) '(150.450000 -141.547500 83.677165)))
(kname ke "Nickel pull")
(ssadd ke ks)
(klay "C-HARDWARE")
(setq ke (kbox '(150.400000 -141.827500 78.970236) '(151.000000 -141.547500 79.250236)))
(kname ke "Pull fixing")
(ssadd ke ks)
(klay "C-HARDWARE")
(setq ke (kbox '(150.400000 -141.827500 82.749764) '(151.000000 -141.547500 83.029764)))
(kname ke "Pull fixing")
(ssadd ke ks)
(klay "C-HARDWARE")
(setq ke (kbox '(151.750000 -126.875000 60.200000) '(153.000000 -125.375000 61.800000)))
(kname ke "Concealed hinge")
(ssadd ke ks)
(klay "C-HARDWARE")
(setq ke (kbox '(151.750000 -126.875000 100.200000) '(153.000000 -125.375000 101.800000)))
(kname ke "Concealed hinge")
(ssadd ke ks)
(klay "C-FRONTS")
(setq ke (kbox '(151.000000 -162.687500 56.062500) '(151.750000 -143.750000 105.937500)))
(kname ke "Door front")
(ssadd ke ks)
(klay "C-HARDWARE")
(setq ke (kbox '(150.015748 -145.827500 78.322835) '(150.450000 -145.547500 83.677165)))
(kname ke "Nickel pull")
(ssadd ke ks)
(klay "C-HARDWARE")
(setq ke (kbox '(150.400000 -145.827500 78.970236) '(151.000000 -145.547500 79.250236)))
(kname ke "Pull fixing")
(ssadd ke ks)
(klay "C-HARDWARE")
(setq ke (kbox '(150.400000 -145.827500 82.749764) '(151.000000 -145.547500 83.029764)))
(kname ke "Pull fixing")
(ssadd ke ks)
(klay "C-HARDWARE")
(setq ke (kbox '(151.750000 -145.937500 60.200000) '(153.000000 -144.437500 61.800000)))
(kname ke "Concealed hinge")
(ssadd ke ks)
(klay "C-HARDWARE")
(setq ke (kbox '(151.750000 -145.937500 100.200000) '(153.000000 -144.437500 101.800000)))
(kname ke "Concealed hinge")
(ssadd ke ks)
(klay "C-CARCASS")
(setq ke (kbox '(152.000000 -162.000000 72.666667) '(164.500000 -125.375000 73.416667)))
(kname ke "Fixed shelf")
(ssadd ke ks)
(klay "C-CARCASS")
(setq ke (kbox '(152.000000 -162.000000 89.333333) '(164.500000 -125.375000 90.083333)))
(kname ke "Fixed shelf")
(ssadd ke ks)
(klay "0") (command "_.-BLOCK" "U-S-124.625" '(0 0 0) ks "")
(klay "0") (command "_.-INSERT" "U-S-124.625" '(0 0 0) 1 1 0)
(setq ks (ssadd))
(klay "C-FRONTS")
(setq ke (kbox '(0.000000 -14.000000 106.000000) '(165.000000 0.000000 108.000000)))
(kname ke "Upper filler")
(ssadd ke ks)
(klay "C-FRONTS")
(setq ke (kbox '(0.000000 -35.250000 106.000000) '(14.000000 0.000000 108.000000)))
(kname ke "Upper filler")
(ssadd ke ks)
(klay "C-FRONTS")
(setq ke (kbox '(151.000000 -163.500000 106.000000) '(165.000000 0.000000 108.000000)))
(kname ke "Upper filler")
(ssadd ke ks)
(klay "0") (command "_.-BLOCK" "UPPER-FILLERS" '(0 0 0) ks "")
(klay "0") (command "_.-INSERT" "UPPER-FILLERS" '(0 0 0) 1 1 0)
(setq ks (ssadd))
(klay "S-PORCELAIN")
(setq ke (kbox '(0.000000 -26.000000 35.527559) '(68.250000 0.000000 36.000000)))
(kname ke "C01 back")
(ssadd ke ks)
(klay "S-PORCELAIN")
(setq ke (kbox '(0.000000 -35.250000 35.527559) '(26.000000 -26.000000 36.000000)))
(kname ke "C01 return")
(ssadd ke ks)
(klay "0") (command "_.-BLOCK" "C01" '(0 0 0) ks "")
(klay "0") (command "_.-INSERT" "C01" '(0 0 0) 1 1 0)
(setq ks (ssadd))
(klay "S-PORCELAIN")
(setq ke (kbox '(98.750000 -26.000000 35.527559) '(165.000000 0.000000 36.000000)))
(kname ke "C02 back")
(ssadd ke ks)
(klay "S-PORCELAIN")
(setq ke (kbox '(139.000000 -42.000000 35.527559) '(165.000000 -26.000000 36.000000)))
(kname ke "C02 return")
(ssadd ke ks)
(klay "0") (command "_.-BLOCK" "C02" '(0 0 0) ks "")
(klay "0") (command "_.-INSERT" "C02" '(0 0 0) 1 1 0)
(setq ks (ssadd))
(klay "S-PORCELAIN")
(setq ke (kbox '(139.000000 -163.500000 35.527559) '(165.000000 -42.000000 36.000000)))
(setq kc (kbox '(142.5 -73.75 34) '(160.5 -44.75 37)))
(command "_.SUBTRACT" ke "" kc "")
(kname ke "C03 sink")
(ssadd ke ks)
(klay "0") (command "_.-BLOCK" "C03" '(0 0 0) ks "")
(klay "0") (command "_.-INSERT" "C03" '(0 0 0) 1 1 0)
(setq ks (ssadd))
(klay "S-PORCELAIN")
(setq ke (kbox '(25.527559 -35.250000 34.500000) '(26.000000 -26.000000 35.527559)))
(kname ke "Left edge")
(ssadd ke ks)
(klay "S-PORCELAIN")
(setq ke (kbox '(0.000000 -26.000000 34.500000) '(68.250000 -25.527559 35.527559)))
(kname ke "Back left edge")
(ssadd ke ks)
(klay "S-PORCELAIN")
(setq ke (kbox '(98.750000 -26.000000 34.500000) '(139.000000 -25.527559 35.527559)))
(kname ke "Back right edge")
(ssadd ke ks)
(klay "S-PORCELAIN")
(setq ke (kbox '(139.000000 -163.500000 34.500000) '(139.472441 -26.000000 35.527559)))
(kname ke "Sink edge")
(ssadd ke ks)
(klay "S-PORCELAIN")
(setq ke (kbox '(139.000000 -163.500000 34.500000) '(165.000000 -163.027559 35.527559)))
(kname ke "Sink outer edge")
(ssadd ke ks)
(klay "0") (command "_.-BLOCK" "COUNTER-FASCIA" '(0 0 0) ks "")
(klay "0") (command "_.-INSERT" "COUNTER-FASCIA" '(0 0 0) 1 1 0)
(setq ks (ssadd))
(klay "S-PORCELAIN")
(setq ke (kbox '(0.000000 -35.250000 36.000000) '(0.472441 0.000000 56.000000)))
(kname ke "B01")
(ssadd ke ks)
(klay "0") (command "_.-BLOCK" "B01" '(0 0 0) ks "")
(klay "0") (command "_.-INSERT" "B01" '(0 0 0) 1 1 0)
(setq ks (ssadd))
(klay "S-PORCELAIN")
(setq ke (kbox '(0.000000 -0.472441 36.000000) '(68.250000 0.000000 56.000000)))
(kname ke "B02")
(ssadd ke ks)
(klay "0") (command "_.-BLOCK" "B02" '(0 0 0) ks "")
(klay "0") (command "_.-INSERT" "B02" '(0 0 0) 1 1 0)
(setq ks (ssadd))
(klay "S-PORCELAIN")
(setq ke (kbox '(98.750000 -0.472441 36.000000) '(165.000000 0.000000 56.000000)))
(kname ke "B04")
(ssadd ke ks)
(klay "0") (command "_.-BLOCK" "B04" '(0 0 0) ks "")
(klay "0") (command "_.-INSERT" "B04" '(0 0 0) 1 1 0)
(setq ks (ssadd))
(klay "S-PORCELAIN")
(setq ke (kbox '(164.527559 -42.000000 36.000000) '(165.000000 0.000000 44.000000)))
(kname ke "B05 low")
(ssadd ke ks)
(klay "S-PORCELAIN")
(setq ke (kbox '(164.527559 -33.250000 44.000000) '(165.000000 0.000000 56.000000)))
(kname ke "B05 high")
(ssadd ke ks)
(klay "0") (command "_.-BLOCK" "B05" '(0 0 0) ks "")
(klay "0") (command "_.-INSERT" "B05" '(0 0 0) 1 1 0)
(setq ks (ssadd))
(klay "S-PORCELAIN")
(setq ke (kbox '(164.527559 -163.500000 36.000000) '(165.000000 -42.000000 44.000000)))
(kname ke "B06 low")
(ssadd ke ks)
(klay "S-PORCELAIN")
(setq ke (kbox '(164.527559 -163.500000 44.000000) '(165.000000 -85.250000 56.000000)))
(kname ke "B06 high")
(ssadd ke ks)
(klay "0") (command "_.-BLOCK" "B06" '(0 0 0) ks "")
(klay "0") (command "_.-INSERT" "B06" '(0 0 0) 1 1 0)
(setq ks (ssadd))
(klay "S-PORCELAIN")
(setq ke (kbox '(164.527559 -33.250000 56.000000) '(165.000000 -32.250000 92.000000)))
(kname ke "W01")
(ssadd ke ks)
(klay "0") (command "_.-BLOCK" "W01" '(0 0 0) ks "")
(klay "0") (command "_.-INSERT" "W01" '(0 0 0) 1 1 0)
(setq ks (ssadd))
(klay "S-PORCELAIN")
(setq ke (kbox '(164.527559 -86.250000 56.000000) '(165.000000 -85.250000 92.000000)))
(kname ke "W02")
(ssadd ke ks)
(klay "0") (command "_.-BLOCK" "W02" '(0 0 0) ks "")
(klay "0") (command "_.-INSERT" "W02" '(0 0 0) 1 1 0)
(setq ks (ssadd))
(klay "S-PORCELAIN")
(setq ke (kbox '(164.527559 -86.250000 92.000000) '(165.000000 -32.250000 108.000000)))
(kname ke "W03")
(ssadd ke ks)
(klay "0") (command "_.-BLOCK" "W03" '(0 0 0) ks "")
(klay "0") (command "_.-INSERT" "W03" '(0 0 0) 1 1 0)
(setq ks (ssadd))
(klay "S-PORCELAIN")
(setq ke (kbox '(164.527559 -85.250000 44.000000) '(166.000000 -33.250000 44.472441)))
(kname ke "W04")
(ssadd ke ks)
(klay "0") (command "_.-BLOCK" "W04" '(0 0 0) ks "")
(klay "0") (command "_.-INSERT" "W04" '(0 0 0) 1 1 0)
(setq ks (ssadd))
(klay "S-PORCELAIN")
(setq ke (kbox '(164.527559 -85.250000 91.527559) '(166.000000 -33.250000 92.000000)))
(kname ke "W05")
(ssadd ke ks)
(klay "0") (command "_.-BLOCK" "W05" '(0 0 0) ks "")
(klay "0") (command "_.-INSERT" "W05" '(0 0 0) 1 1 0)
(setq ks (ssadd))
(klay "S-PORCELAIN")
(setq ke (kbox '(164.527559 -33.722441 44.472441) '(166.000000 -33.250000 91.527559)))
(kname ke "W06")
(ssadd ke ks)
(klay "0") (command "_.-BLOCK" "W06" '(0 0 0) ks "")
(klay "0") (command "_.-INSERT" "W06" '(0 0 0) 1 1 0)
(setq ks (ssadd))
(klay "S-PORCELAIN")
(setq ke (kbox '(164.527559 -85.250000 44.472441) '(166.000000 -84.777559 91.527559)))
(kname ke "W07")
(ssadd ke ks)
(klay "0") (command "_.-BLOCK" "W07" '(0 0 0) ks "")
(klay "0") (command "_.-INSERT" "W07" '(0 0 0) 1 1 0)
(setq ks (ssadd))
(klay "A-JOINERY")
(setq ke (kbox '(166.000000 -34.750000 44.000000) '(167.500000 -33.250000 92.000000)))
(kname ke "Window frame")
(ssadd ke ks)
(klay "A-JOINERY")
(setq ke (kbox '(166.000000 -85.250000 44.000000) '(167.500000 -83.750000 92.000000)))
(kname ke "Window frame")
(ssadd ke ks)
(klay "A-JOINERY")
(setq ke (kbox '(166.000000 -83.750000 44.000000) '(167.500000 -34.750000 45.500000)))
(kname ke "Window frame")
(ssadd ke ks)
(klay "A-JOINERY")
(setq ke (kbox '(166.000000 -83.750000 90.500000) '(167.500000 -34.750000 92.000000)))
(kname ke "Window frame")
(ssadd ke ks)
(klay "A-GLASS")
(setq ke (kbox '(167.000000 -83.750000 45.500000) '(167.150000 -34.750000 90.500000)))
(kname ke "Window glass")
(ssadd ke ks)
(klay "0") (command "_.-BLOCK" "WINDOW" '(0 0 0) ks "")
(klay "0") (command "_.-INSERT" "WINDOW" '(0 0 0) 1 1 0)
(setq ks (ssadd))
(klay "S-PORCELAIN")
(setq ke (kbox '(68.250000 -0.472441 31.000000) '(98.750000 0.000000 56.000000)))
(kname ke "B03 lower 5in below counter")
(ssadd ke ks)
(klay "S-PORCELAIN")
(setq ke (kbox '(67.500000 -0.472441 56.000000) '(99.500000 0.000000 68.245350)))
(kname ke "B03 upper shoulder selected B")
(ssadd ke ks)
(command "_.UNION" ks "")
(setq ke (entlast) ks (ssadd))
(kname ke "B03 stepped range backsplash")
(ssadd ke ks)
(klay "0") (command "_.-BLOCK" "B03" '(0 0 0) ks "")
(klay "0") (command "_.-INSERT" "B03" '(0 0 0) 1 1 0)
(setq ks (ssadd))
(klay "C-CARCASS")
(setq ke (kbox '(77.500000 -86.500000 4.000000) '(98.750000 -85.750000 34.500000)))
(kname ke "Carcass panel")
(ssadd ke ks)
(klay "C-CARCASS")
(setq ke (kbox '(77.500000 -110.750000 4.000000) '(98.750000 -110.000000 34.500000)))
(kname ke "Carcass panel")
(ssadd ke ks)
(klay "C-CARCASS")
(setq ke (kbox '(77.500000 -110.000000 4.000000) '(98.750000 -86.500000 4.750000)))
(kname ke "Carcass panel")
(ssadd ke ks)
(klay "C-CARCASS")
(setq ke (kbox '(77.500000 -110.000000 4.750000) '(78.000000 -86.500000 34.500000)))
(kname ke "Carcass panel")
(ssadd ke ks)
(klay "C-CARCASS")
(setq ke (kbox '(77.500000 -110.000000 33.750000) '(79.500000 -86.500000 34.500000)))
(kname ke "Carcass panel")
(ssadd ke ks)
(klay "C-CARCASS")
(setq ke (kbox '(96.750000 -110.000000 33.750000) '(98.750000 -86.500000 34.500000)))
(kname ke "Carcass panel")
(ssadd ke ks)
(klay "C-PLINTH")
(setq ke (kbox '(80.500000 -110.750000 0.000000) '(97.500000 -85.750000 4.000000)))
(kname ke "Recessed toe kick")
(ssadd ke ks)
(klay "C-FRONTS")
(setq ke (kbox '(98.750000 -110.687500 4.062500) '(99.500000 -85.812500 16.937500)))
(kname ke "Drawer front")
(ssadd ke ks)
(klay "C-CARCASS")
(setq ke (kbox '(79.500000 -109.250000 5.250000) '(98.500000 -87.250000 5.750000)))
(kname ke "Drawer floor")
(ssadd ke ks)
(klay "C-CARCASS")
(setq ke (kbox '(79.500000 -87.250000 5.250000) '(98.500000 -86.750000 12.250000)))
(kname ke "Drawer box")
(ssadd ke ks)
(klay "C-CARCASS")
(setq ke (kbox '(79.500000 -109.750000 5.250000) '(98.500000 -109.250000 12.250000)))
(kname ke "Drawer box")
(ssadd ke ks)
(klay "C-CARCASS")
(setq ke (kbox '(79.500000 -109.250000 5.750000) '(80.000000 -87.250000 12.250000)))
(kname ke "Drawer box")
(ssadd ke ks)
(klay "C-CARCASS")
(setq ke (kbox '(98.000000 -109.250000 5.750000) '(98.500000 -87.250000 12.250000)))
(kname ke "Drawer box")
(ssadd ke ks)
(klay "C-HARDWARE")
(setq ke (kbox '(79.500000 -86.750000 4.950000) '(98.500000 -86.550000 5.650000)))
(kname ke "Runner profile")
(ssadd ke ks)
(klay "C-HARDWARE")
(setq ke (kbox '(79.500000 -109.950000 4.950000) '(98.500000 -109.750000 5.650000)))
(kname ke "Runner profile")
(ssadd ke ks)
(klay "C-HARDWARE")
(setq ke (kbox '(100.050000 -100.927165 13.860000) '(100.484252 -95.572835 14.140000)))
(kname ke "Nickel pull")
(ssadd ke ks)
(klay "C-HARDWARE")
(setq ke (kbox '(99.500000 -96.500236 13.860000) '(100.100000 -96.220236 14.140000)))
(kname ke "Pull fixing")
(ssadd ke ks)
(klay "C-HARDWARE")
(setq ke (kbox '(99.500000 -100.279764 13.860000) '(100.100000 -99.999764 14.140000)))
(kname ke "Pull fixing")
(ssadd ke ks)
(klay "C-FRONTS")
(setq ke (kbox '(98.750000 -110.687500 17.062500) '(99.500000 -85.812500 25.687500)))
(kname ke "Drawer front")
(ssadd ke ks)
(klay "C-CARCASS")
(setq ke (kbox '(79.500000 -109.250000 18.250000) '(98.500000 -87.250000 18.750000)))
(kname ke "Drawer floor")
(ssadd ke ks)
(klay "C-CARCASS")
(setq ke (kbox '(79.500000 -87.250000 18.250000) '(98.500000 -86.750000 24.500000)))
(kname ke "Drawer box")
(ssadd ke ks)
(klay "C-CARCASS")
(setq ke (kbox '(79.500000 -109.750000 18.250000) '(98.500000 -109.250000 24.500000)))
(kname ke "Drawer box")
(ssadd ke ks)
(klay "C-CARCASS")
(setq ke (kbox '(79.500000 -109.250000 18.750000) '(80.000000 -87.250000 24.500000)))
(kname ke "Drawer box")
(ssadd ke ks)
(klay "C-CARCASS")
(setq ke (kbox '(98.000000 -109.250000 18.750000) '(98.500000 -87.250000 24.500000)))
(kname ke "Drawer box")
(ssadd ke ks)
(klay "C-HARDWARE")
(setq ke (kbox '(79.500000 -86.750000 17.950000) '(98.500000 -86.550000 18.650000)))
(kname ke "Runner profile")
(ssadd ke ks)
(klay "C-HARDWARE")
(setq ke (kbox '(79.500000 -109.950000 17.950000) '(98.500000 -109.750000 18.650000)))
(kname ke "Runner profile")
(ssadd ke ks)
(klay "C-HARDWARE")
(setq ke (kbox '(100.050000 -100.927165 22.610000) '(100.484252 -95.572835 22.890000)))
(kname ke "Nickel pull")
(ssadd ke ks)
(klay "C-HARDWARE")
(setq ke (kbox '(99.500000 -96.500236 22.610000) '(100.100000 -96.220236 22.890000)))
(kname ke "Pull fixing")
(ssadd ke ks)
(klay "C-HARDWARE")
(setq ke (kbox '(99.500000 -100.279764 22.610000) '(100.100000 -99.999764 22.890000)))
(kname ke "Pull fixing")
(ssadd ke ks)
(klay "C-FRONTS")
(setq ke (kbox '(98.750000 -110.687500 25.812500) '(99.500000 -85.812500 34.437500)))
(kname ke "Drawer front")
(ssadd ke ks)
(klay "C-CARCASS")
(setq ke (kbox '(79.500000 -109.250000 27.000000) '(98.500000 -87.250000 27.500000)))
(kname ke "Drawer floor")
(ssadd ke ks)
(klay "C-CARCASS")
(setq ke (kbox '(79.500000 -87.250000 27.000000) '(98.500000 -86.750000 33.250000)))
(kname ke "Drawer box")
(ssadd ke ks)
(klay "C-CARCASS")
(setq ke (kbox '(79.500000 -109.750000 27.000000) '(98.500000 -109.250000 33.250000)))
(kname ke "Drawer box")
(ssadd ke ks)
(klay "C-CARCASS")
(setq ke (kbox '(79.500000 -109.250000 27.500000) '(80.000000 -87.250000 33.250000)))
(kname ke "Drawer box")
(ssadd ke ks)
(klay "C-CARCASS")
(setq ke (kbox '(98.000000 -109.250000 27.500000) '(98.500000 -87.250000 33.250000)))
(kname ke "Drawer box")
(ssadd ke ks)
(klay "C-HARDWARE")
(setq ke (kbox '(79.500000 -86.750000 26.700000) '(98.500000 -86.550000 27.400000)))
(kname ke "Runner profile")
(ssadd ke ks)
(klay "C-HARDWARE")
(setq ke (kbox '(79.500000 -109.950000 26.700000) '(98.500000 -109.750000 27.400000)))
(kname ke "Runner profile")
(ssadd ke ks)
(klay "C-HARDWARE")
(setq ke (kbox '(100.050000 -100.927165 31.360000) '(100.484252 -95.572835 31.640000)))
(kname ke "Nickel pull")
(ssadd ke ks)
(klay "C-HARDWARE")
(setq ke (kbox '(99.500000 -96.500236 31.360000) '(100.100000 -96.220236 31.640000)))
(kname ke "Pull fixing")
(ssadd ke ks)
(klay "C-HARDWARE")
(setq ke (kbox '(99.500000 -100.279764 31.360000) '(100.100000 -99.999764 31.640000)))
(kname ke "Pull fixing")
(ssadd ke ks)
(klay "0") (command "_.-BLOCK" "ISLAND-MAIN-1" '(0 0 0) ks "")
(klay "0") (command "_.-INSERT" "ISLAND-MAIN-1" '(0 0 0) 1 1 0)
(setq ks (ssadd))
(klay "C-CARCASS")
(setq ke (kbox '(77.500000 -111.500000 4.000000) '(98.750000 -110.750000 34.500000)))
(kname ke "Carcass panel")
(ssadd ke ks)
(klay "C-CARCASS")
(setq ke (kbox '(77.500000 -135.750000 4.000000) '(98.750000 -135.000000 34.500000)))
(kname ke "Carcass panel")
(ssadd ke ks)
(klay "C-CARCASS")
(setq ke (kbox '(77.500000 -135.000000 4.000000) '(98.750000 -111.500000 4.750000)))
(kname ke "Carcass panel")
(ssadd ke ks)
(klay "C-CARCASS")
(setq ke (kbox '(77.500000 -135.000000 4.750000) '(78.000000 -111.500000 34.500000)))
(kname ke "Carcass panel")
(ssadd ke ks)
(klay "C-CARCASS")
(setq ke (kbox '(77.500000 -135.000000 33.750000) '(79.500000 -111.500000 34.500000)))
(kname ke "Carcass panel")
(ssadd ke ks)
(klay "C-CARCASS")
(setq ke (kbox '(96.750000 -135.000000 33.750000) '(98.750000 -111.500000 34.500000)))
(kname ke "Carcass panel")
(ssadd ke ks)
(klay "C-PLINTH")
(setq ke (kbox '(80.500000 -135.750000 0.000000) '(97.500000 -110.750000 4.000000)))
(kname ke "Recessed toe kick")
(ssadd ke ks)
(klay "C-FRONTS")
(setq ke (kbox '(98.750000 -135.687500 4.062500) '(99.500000 -110.812500 16.937500)))
(kname ke "Drawer front")
(ssadd ke ks)
(klay "C-CARCASS")
(setq ke (kbox '(79.500000 -134.250000 5.250000) '(98.500000 -112.250000 5.750000)))
(kname ke "Drawer floor")
(ssadd ke ks)
(klay "C-CARCASS")
(setq ke (kbox '(79.500000 -112.250000 5.250000) '(98.500000 -111.750000 12.250000)))
(kname ke "Drawer box")
(ssadd ke ks)
(klay "C-CARCASS")
(setq ke (kbox '(79.500000 -134.750000 5.250000) '(98.500000 -134.250000 12.250000)))
(kname ke "Drawer box")
(ssadd ke ks)
(klay "C-CARCASS")
(setq ke (kbox '(79.500000 -134.250000 5.750000) '(80.000000 -112.250000 12.250000)))
(kname ke "Drawer box")
(ssadd ke ks)
(klay "C-CARCASS")
(setq ke (kbox '(98.000000 -134.250000 5.750000) '(98.500000 -112.250000 12.250000)))
(kname ke "Drawer box")
(ssadd ke ks)
(klay "C-HARDWARE")
(setq ke (kbox '(79.500000 -111.750000 4.950000) '(98.500000 -111.550000 5.650000)))
(kname ke "Runner profile")
(ssadd ke ks)
(klay "C-HARDWARE")
(setq ke (kbox '(79.500000 -134.950000 4.950000) '(98.500000 -134.750000 5.650000)))
(kname ke "Runner profile")
(ssadd ke ks)
(klay "C-HARDWARE")
(setq ke (kbox '(100.050000 -125.927165 13.860000) '(100.484252 -120.572835 14.140000)))
(kname ke "Nickel pull")
(ssadd ke ks)
(klay "C-HARDWARE")
(setq ke (kbox '(99.500000 -121.500236 13.860000) '(100.100000 -121.220236 14.140000)))
(kname ke "Pull fixing")
(ssadd ke ks)
(klay "C-HARDWARE")
(setq ke (kbox '(99.500000 -125.279764 13.860000) '(100.100000 -124.999764 14.140000)))
(kname ke "Pull fixing")
(ssadd ke ks)
(klay "C-FRONTS")
(setq ke (kbox '(98.750000 -135.687500 17.062500) '(99.500000 -110.812500 25.687500)))
(kname ke "Drawer front")
(ssadd ke ks)
(klay "C-CARCASS")
(setq ke (kbox '(79.500000 -134.250000 18.250000) '(98.500000 -112.250000 18.750000)))
(kname ke "Drawer floor")
(ssadd ke ks)
(klay "C-CARCASS")
(setq ke (kbox '(79.500000 -112.250000 18.250000) '(98.500000 -111.750000 24.500000)))
(kname ke "Drawer box")
(ssadd ke ks)
(klay "C-CARCASS")
(setq ke (kbox '(79.500000 -134.750000 18.250000) '(98.500000 -134.250000 24.500000)))
(kname ke "Drawer box")
(ssadd ke ks)
(klay "C-CARCASS")
(setq ke (kbox '(79.500000 -134.250000 18.750000) '(80.000000 -112.250000 24.500000)))
(kname ke "Drawer box")
(ssadd ke ks)
(klay "C-CARCASS")
(setq ke (kbox '(98.000000 -134.250000 18.750000) '(98.500000 -112.250000 24.500000)))
(kname ke "Drawer box")
(ssadd ke ks)
(klay "C-HARDWARE")
(setq ke (kbox '(79.500000 -111.750000 17.950000) '(98.500000 -111.550000 18.650000)))
(kname ke "Runner profile")
(ssadd ke ks)
(klay "C-HARDWARE")
(setq ke (kbox '(79.500000 -134.950000 17.950000) '(98.500000 -134.750000 18.650000)))
(kname ke "Runner profile")
(ssadd ke ks)
(klay "C-HARDWARE")
(setq ke (kbox '(100.050000 -125.927165 22.610000) '(100.484252 -120.572835 22.890000)))
(kname ke "Nickel pull")
(ssadd ke ks)
(klay "C-HARDWARE")
(setq ke (kbox '(99.500000 -121.500236 22.610000) '(100.100000 -121.220236 22.890000)))
(kname ke "Pull fixing")
(ssadd ke ks)
(klay "C-HARDWARE")
(setq ke (kbox '(99.500000 -125.279764 22.610000) '(100.100000 -124.999764 22.890000)))
(kname ke "Pull fixing")
(ssadd ke ks)
(klay "C-FRONTS")
(setq ke (kbox '(98.750000 -135.687500 25.812500) '(99.500000 -110.812500 34.437500)))
(kname ke "Drawer front")
(ssadd ke ks)
(klay "C-CARCASS")
(setq ke (kbox '(79.500000 -134.250000 27.000000) '(98.500000 -112.250000 27.500000)))
(kname ke "Drawer floor")
(ssadd ke ks)
(klay "C-CARCASS")
(setq ke (kbox '(79.500000 -112.250000 27.000000) '(98.500000 -111.750000 33.250000)))
(kname ke "Drawer box")
(ssadd ke ks)
(klay "C-CARCASS")
(setq ke (kbox '(79.500000 -134.750000 27.000000) '(98.500000 -134.250000 33.250000)))
(kname ke "Drawer box")
(ssadd ke ks)
(klay "C-CARCASS")
(setq ke (kbox '(79.500000 -134.250000 27.500000) '(80.000000 -112.250000 33.250000)))
(kname ke "Drawer box")
(ssadd ke ks)
(klay "C-CARCASS")
(setq ke (kbox '(98.000000 -134.250000 27.500000) '(98.500000 -112.250000 33.250000)))
(kname ke "Drawer box")
(ssadd ke ks)
(klay "C-HARDWARE")
(setq ke (kbox '(79.500000 -111.750000 26.700000) '(98.500000 -111.550000 27.400000)))
(kname ke "Runner profile")
(ssadd ke ks)
(klay "C-HARDWARE")
(setq ke (kbox '(79.500000 -134.950000 26.700000) '(98.500000 -134.750000 27.400000)))
(kname ke "Runner profile")
(ssadd ke ks)
(klay "C-HARDWARE")
(setq ke (kbox '(100.050000 -125.927165 31.360000) '(100.484252 -120.572835 31.640000)))
(kname ke "Nickel pull")
(ssadd ke ks)
(klay "C-HARDWARE")
(setq ke (kbox '(99.500000 -121.500236 31.360000) '(100.100000 -121.220236 31.640000)))
(kname ke "Pull fixing")
(ssadd ke ks)
(klay "C-HARDWARE")
(setq ke (kbox '(99.500000 -125.279764 31.360000) '(100.100000 -124.999764 31.640000)))
(kname ke "Pull fixing")
(ssadd ke ks)
(klay "0") (command "_.-BLOCK" "ISLAND-MAIN-2" '(0 0 0) ks "")
(klay "0") (command "_.-INSERT" "ISLAND-MAIN-2" '(0 0 0) 1 1 0)
(setq ks (ssadd))
(klay "C-CARCASS")
(setq ke (kbox '(80.000000 -109.000000 31.000000) '(97.750000 -87.500000 31.500000)))
(kname ke "Concealed inner tray")
(ssadd ke ks)
(klay "C-CARCASS")
(setq ke (kbox '(80.000000 -87.500000 31.000000) '(97.750000 -87.000000 33.750000)))
(kname ke "Concealed inner tray")
(ssadd ke ks)
(klay "C-CARCASS")
(setq ke (kbox '(80.000000 -109.500000 31.000000) '(97.750000 -109.000000 33.750000)))
(kname ke "Concealed inner tray")
(ssadd ke ks)
(klay "C-CARCASS")
(setq ke (kbox '(80.000000 -109.000000 31.500000) '(80.500000 -87.500000 33.750000)))
(kname ke "Concealed inner tray")
(ssadd ke ks)
(klay "C-CARCASS")
(setq ke (kbox '(97.250000 -109.000000 31.500000) '(97.750000 -87.500000 33.750000)))
(kname ke "Concealed inner tray")
(ssadd ke ks)
(klay "0") (command "_.-BLOCK" "ISLAND-INNER-85.75" '(0 0 0) ks "")
(klay "0") (command "_.-INSERT" "ISLAND-INNER-85.75" '(0 0 0) 1 1 0)
(setq ks (ssadd))
(klay "C-CARCASS")
(setq ke (kbox '(80.000000 -134.000000 31.000000) '(97.750000 -112.500000 31.500000)))
(kname ke "Concealed inner tray")
(ssadd ke ks)
(klay "C-CARCASS")
(setq ke (kbox '(80.000000 -112.500000 31.000000) '(97.750000 -112.000000 33.750000)))
(kname ke "Concealed inner tray")
(ssadd ke ks)
(klay "C-CARCASS")
(setq ke (kbox '(80.000000 -134.500000 31.000000) '(97.750000 -134.000000 33.750000)))
(kname ke "Concealed inner tray")
(ssadd ke ks)
(klay "C-CARCASS")
(setq ke (kbox '(80.000000 -134.000000 31.500000) '(80.500000 -112.500000 33.750000)))
(kname ke "Concealed inner tray")
(ssadd ke ks)
(klay "C-CARCASS")
(setq ke (kbox '(97.250000 -134.000000 31.500000) '(97.750000 -112.500000 33.750000)))
(kname ke "Concealed inner tray")
(ssadd ke ks)
(klay "0") (command "_.-BLOCK" "ISLAND-INNER-110.75" '(0 0 0) ks "")
(klay "0") (command "_.-INSERT" "ISLAND-INNER-110.75" '(0 0 0) 1 1 0)
(setq ks (ssadd))
(klay "C-FRONTS")
(setq ke (kbox '(77.500000 -85.750000 4.000000) '(78.250000 -73.000000 34.500000)))
(kname ke "Tray bay side")
(ssadd ke ks)
(klay "C-FRONTS")
(setq ke (kbox '(98.750000 -85.750000 4.000000) '(99.500000 -73.000000 34.500000)))
(kname ke "Tray bay side")
(ssadd ke ks)
(klay "C-CARCASS")
(setq ke (kbox '(78.250000 -73.750000 4.000000) '(98.750000 -73.000000 4.750000)))
(kname ke "Fixed rail")
(ssadd ke ks)
(klay "C-CARCASS")
(setq ke (kbox '(78.250000 -73.750000 16.000000) '(98.750000 -73.000000 16.750000)))
(kname ke "Fixed rail")
(ssadd ke ks)
(klay "C-CARCASS")
(setq ke (kbox '(78.250000 -73.750000 25.250000) '(98.750000 -73.000000 26.000000)))
(kname ke "Fixed rail")
(ssadd ke ks)
(klay "0") (command "_.-BLOCK" "ISLAND-END-CARCASS" '(0 0 0) ks "")
(klay "0") (command "_.-INSERT" "ISLAND-END-CARCASS" '(0 0 0) 1 1 0)
(setq ks (ssadd))
(klay "C-CARCASS")
(setq ke (kbox '(78.900000 -84.700000 5.100000) '(98.100000 -74.000000 5.600000)))
(kname ke "Tray floor")
(ssadd ke ks)
(klay "C-GLASS")
(setq ke (kbox '(78.900000 -73.950000 5.600000) '(98.100000 -73.700000 11.600000)))
(kname ke "Glass front")
(ssadd ke ks)
(klay "C-CARCASS")
(setq ke (kbox '(78.400000 -84.700000 5.100000) '(78.900000 -74.000000 12.000000)))
(kname ke "Tray side")
(ssadd ke ks)
(klay "C-CARCASS")
(setq ke (kbox '(98.100000 -84.700000 5.100000) '(98.600000 -74.000000 12.000000)))
(kname ke "Tray side")
(ssadd ke ks)
(klay "C-CARCASS")
(setq ke (kbox '(78.900000 -84.700000 5.600000) '(98.100000 -84.200000 12.000000)))
(kname ke "Tray back")
(ssadd ke ks)
(klay "C-HARDWARE")
(setq ke (kbox '(78.300000 -84.500000 4.800000) '(78.450000 -74.000000 5.500000)))
(kname ke "Tray runner")
(ssadd ke ks)
(klay "C-HARDWARE")
(setq ke (kbox '(98.600000 -84.500000 4.800000) '(98.750000 -74.000000 5.500000)))
(kname ke "Tray runner")
(ssadd ke ks)
(klay "0") (command "_.-BLOCK" "ISLAND-END-TRAY-1" '(0 0 0) ks "")
(klay "0") (command "_.-INSERT" "ISLAND-END-TRAY-1" '(0 0 0) 1 1 0)
(setq ks (ssadd))
(klay "C-CARCASS")
(setq ke (kbox '(78.900000 -84.700000 17.100000) '(98.100000 -74.000000 17.600000)))
(kname ke "Tray floor")
(ssadd ke ks)
(klay "C-GLASS")
(setq ke (kbox '(78.900000 -73.950000 17.600000) '(98.100000 -73.700000 22.100000)))
(kname ke "Glass front")
(ssadd ke ks)
(klay "C-CARCASS")
(setq ke (kbox '(78.400000 -84.700000 17.100000) '(78.900000 -74.000000 22.500000)))
(kname ke "Tray side")
(ssadd ke ks)
(klay "C-CARCASS")
(setq ke (kbox '(98.100000 -84.700000 17.100000) '(98.600000 -74.000000 22.500000)))
(kname ke "Tray side")
(ssadd ke ks)
(klay "C-CARCASS")
(setq ke (kbox '(78.900000 -84.700000 17.600000) '(98.100000 -84.200000 22.500000)))
(kname ke "Tray back")
(ssadd ke ks)
(klay "C-HARDWARE")
(setq ke (kbox '(78.300000 -84.500000 16.800000) '(78.450000 -74.000000 17.500000)))
(kname ke "Tray runner")
(ssadd ke ks)
(klay "C-HARDWARE")
(setq ke (kbox '(98.600000 -84.500000 16.800000) '(98.750000 -74.000000 17.500000)))
(kname ke "Tray runner")
(ssadd ke ks)
(klay "0") (command "_.-BLOCK" "ISLAND-END-TRAY-2" '(0 0 0) ks "")
(klay "0") (command "_.-INSERT" "ISLAND-END-TRAY-2" '(0 0 0) 1 1 0)
(setq ks (ssadd))
(klay "C-CARCASS")
(setq ke (kbox '(78.900000 -84.700000 26.350000) '(98.100000 -74.000000 26.850000)))
(kname ke "Tray floor")
(ssadd ke ks)
(klay "C-GLASS")
(setq ke (kbox '(78.900000 -73.950000 26.850000) '(98.100000 -73.700000 31.350000)))
(kname ke "Glass front")
(ssadd ke ks)
(klay "C-CARCASS")
(setq ke (kbox '(78.400000 -84.700000 26.350000) '(78.900000 -74.000000 31.750000)))
(kname ke "Tray side")
(ssadd ke ks)
(klay "C-CARCASS")
(setq ke (kbox '(98.100000 -84.700000 26.350000) '(98.600000 -74.000000 31.750000)))
(kname ke "Tray side")
(ssadd ke ks)
(klay "C-CARCASS")
(setq ke (kbox '(78.900000 -84.700000 26.850000) '(98.100000 -84.200000 31.750000)))
(kname ke "Tray back")
(ssadd ke ks)
(klay "C-HARDWARE")
(setq ke (kbox '(78.300000 -84.500000 26.050000) '(78.450000 -74.000000 26.750000)))
(kname ke "Tray runner")
(ssadd ke ks)
(klay "C-HARDWARE")
(setq ke (kbox '(98.600000 -84.500000 26.050000) '(98.750000 -74.000000 26.750000)))
(kname ke "Tray runner")
(ssadd ke ks)
(klay "0") (command "_.-BLOCK" "ISLAND-END-TRAY-3" '(0 0 0) ks "")
(klay "0") (command "_.-INSERT" "ISLAND-END-TRAY-3" '(0 0 0) 1 1 0)
(setq ks (ssadd))
(klay "S-PORCELAIN")
(setq ke (kbox '(67.500000 -138.000000 35.527559) '(99.500000 -72.000000 36.000000)))
(kname ke "I01 island top")
(ssadd ke ks)
(klay "0") (command "_.-BLOCK" "I01" '(0 0 0) ks "")
(klay "0") (command "_.-INSERT" "I01" '(0 0 0) 1 1 0)
(setq ks (ssadd))
(klay "S-PORCELAIN")
(setq ke (kbox '(67.500000 -138.000000 0.000000) '(99.500000 -137.527559 35.527559)))
(kname ke "I02 outer waterfall")
(ssadd ke ks)
(klay "S-PORCELAIN")
(setq ke (kbox '(67.500000 -137.527559 0.000000) '(67.972441 -136.500000 34.500000)))
(kname ke "Waterfall return")
(ssadd ke ks)
(klay "S-PORCELAIN")
(setq ke (kbox '(99.027559 -137.527559 0.000000) '(99.500000 -136.500000 34.500000)))
(kname ke "Waterfall return")
(ssadd ke ks)
(klay "0") (command "_.-BLOCK" "I02" '(0 0 0) ks "")
(klay "0") (command "_.-INSERT" "I02" '(0 0 0) 1 1 0)
(setq ks (ssadd))
(klay "S-PORCELAIN")
(setq ke (kbox '(67.500000 -137.527559 34.500000) '(67.972441 -72.000000 35.527559)))
(kname ke "Island edge")
(ssadd ke ks)
(klay "S-PORCELAIN")
(setq ke (kbox '(99.027559 -137.527559 34.500000) '(99.500000 -72.000000 35.527559)))
(kname ke "Island edge")
(ssadd ke ks)
(klay "S-PORCELAIN")
(setq ke (kbox '(67.500000 -72.472441 34.500000) '(99.500000 -72.000000 35.527559)))
(kname ke "Range end edge")
(ssadd ke ks)
(klay "0") (command "_.-BLOCK" "I01-EDGES" '(0 0 0) ks "")
(klay "0") (command "_.-INSERT" "I01-EDGES" '(0 0 0) 1 1 0)
(setq ks (ssadd))
(klay "C-CARCASS")
(setq ke (kbox '(68.000000 -137.500000 0.000000) '(99.000000 -136.500000 34.500000)))
(kname ke "Waterfall backing")
(ssadd ke ks)
(klay "0") (command "_.-BLOCK" "I02-BACKING" '(0 0 0) ks "")
(klay "0") (command "_.-INSERT" "I02-BACKING" '(0 0 0) 1 1 0)
(setq ks (ssadd))
(klay "S-PORCELAIN")
(setq ke (kbox '(77.500000 -104.750000 0.000000) '(77.972441 -73.000000 34.500000)))
(kname ke "I03 flush seating stone")
(ssadd ke ks)
(klay "0") (command "_.-BLOCK" "I03" '(0 0 0) ks "")
(klay "0") (command "_.-INSERT" "I03" '(0 0 0) 1 1 0)
(setq ks (ssadd))
(klay "C-FRONTS")
(setq ke (kbox '(77.500000 -136.500000 0.000000) '(78.250000 -104.750000 34.500000)))
(kname ke "Seating laminate")
(ssadd ke ks)
(klay "0") (command "_.-BLOCK" "ISLAND-SEATING" '(0 0 0) ks "")
(klay "0") (command "_.-INSERT" "ISLAND-SEATING" '(0 0 0) 1 1 0)
(setq ks (ssadd))
(klay "C-CARCASS")
(setq ke (kbox '(68.000000 -137.500000 34.750000) '(99.000000 -72.500000 35.500000)))
(kname ke "Island substrate")
(ssadd ke ks)
(klay "0") (command "_.-BLOCK" "ISLAND-SUBSTRATE" '(0 0 0) ks "")
(klay "0") (command "_.-INSERT" "ISLAND-SUBSTRATE" '(0 0 0) 1 1 0)
(setq ks (ssadd))
(klay "E-LIGHT")
(setq ke (kbox '(72.600000 -136.500000 34.550000) '(72.900000 -73.000000 34.750000)))
(kname ke "LED channel")
(ssadd ke ks)
(klay "0") (command "_.-BLOCK" "ISLAND-LED" '(0 0 0) ks "")
(klay "0") (command "_.-INSERT" "ISLAND-LED" '(0 0 0) 1 1 0)
(setq ks (ssadd))
(klay "S-PORCELAIN")
(setq ke (kbox '(50.500000 -14.000000 56.000000) '(67.500000 -13.500000 108.000000)))
(kname ke "H01")
(ssadd ke ks)
(klay "S-PORCELAIN")
(setq ke (kbox '(99.500000 -14.000000 56.000000) '(116.500000 -13.500000 108.000000)))
(kname ke "H04")
(ssadd ke ks)
(klay "S-PORCELAIN")
(setq ke (kbox '(67.500000 -20.275590 68.245350) '(83.500000 -19.803149 108.000000)))
(kname ke "H02")
(ssadd ke ks)
(klay "S-PORCELAIN")
(setq ke (kbox '(83.500000 -20.275590 68.245350) '(99.500000 -19.803149 108.000000)))
(kname ke "H03")
(ssadd ke ks)
(klay "S-PORCELAIN")
(setq ke (kbox '(67.500000 -19.803149 68.245350) '(67.972441 -14.000000 108.000000)))
(kname ke "H05")
(ssadd ke ks)
(klay "S-PORCELAIN")
(setq ke (kbox '(99.027559 -19.803149 68.245350) '(99.500000 -14.000000 108.000000)))
(kname ke "H06")
(ssadd ke ks)
(klay "0") (command "_.-BLOCK" "HOOD-B-STONE" '(0 0 0) ks "")
(klay "0") (command "_.-INSERT" "HOOD-B-STONE" '(0 0 0) 1 1 0)
(setq ks (ssadd))
(klay "C-CARCASS")
(setq ke (kbox '(50.500000 -13.500000 56.000000) '(67.500000 -12.750000 106.000000)))
(kname ke "Hood backing")
(ssadd ke ks)
(klay "C-CARCASS")
(setq ke (kbox '(51.250000 -12.750000 66.000000) '(66.750000 -0.500000 66.750000)))
(kname ke "Hood shelf")
(ssadd ke ks)
(klay "C-CARCASS")
(setq ke (kbox '(51.250000 -12.750000 81.000000) '(66.750000 -0.500000 81.750000)))
(kname ke "Hood shelf")
(ssadd ke ks)
(klay "C-CARCASS")
(setq ke (kbox '(51.250000 -12.750000 96.000000) '(66.750000 -0.500000 96.750000)))
(kname ke "Hood shelf")
(ssadd ke ks)
(klay "C-CARCASS")
(setq ke (kbox '(99.500000 -13.500000 56.000000) '(116.500000 -12.750000 106.000000)))
(kname ke "Hood backing")
(ssadd ke ks)
(klay "C-CARCASS")
(setq ke (kbox '(100.250000 -12.750000 66.000000) '(115.750000 -0.500000 66.750000)))
(kname ke "Hood shelf")
(ssadd ke ks)
(klay "C-CARCASS")
(setq ke (kbox '(100.250000 -12.750000 81.000000) '(115.750000 -0.500000 81.750000)))
(kname ke "Hood shelf")
(ssadd ke ks)
(klay "C-CARCASS")
(setq ke (kbox '(100.250000 -12.750000 96.000000) '(115.750000 -0.500000 96.750000)))
(kname ke "Hood shelf")
(ssadd ke ks)
(klay "C-CARCASS")
(setq ke (kbox '(67.500000 -19.800000 68.245350) '(99.500000 -19.050000 106.000000)))
(kname ke "Hood centre backing")
(ssadd ke ks)
(klay "0") (command "_.-BLOCK" "HOOD-B-BACKING" '(0 0 0) ks "")
(klay "0") (command "_.-INSERT" "HOOD-B-BACKING" '(0 0 0) 1 1 0)
(setq ks (ssadd))
(klay "M-METAL")
(setq ke (kbox '(68.500000 -20.000000 66.080000) '(98.500000 -1.000000 68.245350)))
(kname ke "Retained Sakura fascia")
(ssadd ke ks)
(klay "E-LIGHT")
(command "_.CYLINDER" '(75.000000 -16.000000 66.000000) 1.2 0.08)
(setq ke (entlast))
(kname ke "Hood lens")
(ssadd ke ks)
(klay "E-LIGHT")
(command "_.CYLINDER" '(91.000000 -16.000000 66.000000) 1.2 0.08)
(setq ke (entlast))
(kname ke "Hood lens")
(ssadd ke ks)
(klay "M-METAL")
(setq ke (kbox '(69.500000 -16.000000 66.048000) '(82.500000 -2.000000 66.080000)))
(kname ke "Filter panel")
(ssadd ke ks)
(klay "M-METAL")
(setq ke (kbox '(84.000000 -16.000000 66.048000) '(97.000000 -2.000000 66.080000)))
(kname ke "Filter panel")
(ssadd ke ks)
(klay "0") (command "_.-BLOCK" "SAKURA-HOOD-PROVISIONAL" '(0 0 0) ks "")
(klay "0") (command "_.-INSERT" "SAKURA-HOOD-PROVISIONAL" '(0 0 0) 1 1 0)
(setq ks (ssadd))
(klay "M-DUCT")
(command "_.CYLINDER" '(83.500000 -8.000000 68.245350) 3 39.75465)
(setq ke (entlast))
(kname ke "Provisional 6in duct")
(ssadd ke ks)
(klay "0") (command "_.-BLOCK" "HOOD-DUCT" '(0 0 0) ks "")
(klay "0") (command "_.-INSERT" "HOOD-DUCT" '(0 0 0) 1 1 0)
(setq ks (ssadd))
(klay "M-METAL")
(setq ke (kbox '(142.850001 -115.699993 0.250000) '(143.350000 -92.299998 4.750000)))
(kname ke "BOSCH bottomtoe")
(ssadd ke ks)
(klay "M-METAL")
(setq ke (kbox '(164.200000 -115.650001 0.262500) '(164.500000 -92.349991 34.137500)))
(kname ke "BOSCH case back")
(ssadd ke ks)
(klay "M-METAL")
(setq ke (kbox '(142.099999 -115.650001 0.250000) '(164.500000 -92.349991 0.550000)))
(kname ke "BOSCH case cap")
(ssadd ke ks)
(klay "M-METAL")
(setq ke (kbox '(142.099999 -115.650001 33.649999) '(164.500000 -92.349991 33.949998)))
(kname ke "BOSCH case cap.001")
(ssadd ke ks)
(klay "M-METAL")
(setq ke (kbox '(142.099999 -92.480004 0.262500) '(164.500000 -92.219997 34.137500)))
(kname ke "BOSCH case side")
(ssadd ke ks)
(klay "M-METAL")
(setq ke (kbox '(142.099999 -115.780004 0.262500) '(164.500000 -115.519997 34.137500)))
(kname ke "BOSCH case side.001")
(ssadd ke ks)
(klay "M-METAL")
(setq ke (kbox '(140.750000 -112.099995 27.989999) '(140.950000 -95.899997 28.210001)))
(kname ke "BOSCH pockethandle lowerlip")
(ssadd ke ks)
(klay "M-METAL")
(setq ke (kbox '(140.780000 -112.399999 28.175001) '(140.880000 -95.599993 29.424999)))
(kname ke "BOSCH pockethandle recess")
(ssadd ke ks)
(klay "M-METAL")
(setq ke (kbox '(140.750000 -112.499994 29.349998) '(140.950000 -95.499998 30.450000)))
(kname ke "BOSCH pockethandle upperlip")
(ssadd ke ks)
(klay "M-METAL")
(setq ke (kbox '(140.750000 -92.339994 5.600000) '(141.899999 -92.219997 33.899999)))
(kname ke "BOSCH stainless door edge")
(ssadd ke ks)
(klay "M-METAL")
(setq ke (kbox '(140.750000 -115.779995 5.600000) '(141.899999 -115.659997 33.899999)))
(kname ke "BOSCH stainless door edge.001")
(ssadd ke ks)
(klay "M-METAL")
(setq ke (kbox '(140.750000 -115.650001 5.550000) '(141.899999 -92.349991 5.670000)))
(kname ke "BOSCH stainless door endcap")
(ssadd ke ks)
(klay "M-METAL")
(setq ke (kbox '(140.750000 -115.650001 33.830001) '(141.899999 -92.349991 33.949998)))
(kname ke "BOSCH stainless door endcap.001")
(ssadd ke ks)
(klay "M-METAL")
(setq ke (kbox '(140.750000 -115.781243 5.549998) '(140.869998 -92.218748 33.949998)))
(kname ke "BOSCH stainless door frontskin")
(ssadd ke ks)
(klay "M-METAL")
(setq ke (kbox '(164.070000 -115.299995 5.700000) '(164.170000 -92.699997 33.099999)))
(kname ke "BOSCH stainless tub back")
(ssadd ke ks)
(klay "M-METAL")
(setq ke (kbox '(142.600000 -115.299995 33.440001) '(164.000001 -92.699997 33.559999)))
(kname ke "BOSCH stainless tub ceiling")
(ssadd ke ks)
(klay "M-METAL")
(setq ke (kbox '(142.600000 -115.299995 4.840000) '(164.000001 -92.699997 4.960000)))
(kname ke "BOSCH stainless tub floor")
(ssadd ke ks)
(klay "M-METAL")
(setq ke (kbox '(142.600000 -92.620005 5.700000) '(164.000001 -92.520000 33.099999)))
(kname ke "BOSCH stainless tub side")
(ssadd ke ks)
(klay "M-METAL")
(setq ke (kbox '(142.600000 -115.480001 5.700000) '(164.000001 -115.379996 33.099999)))
(kname ke "BOSCH stainless tub side.001")
(ssadd ke ks)
(klay "0") (command "_.-BLOCK" "AP-BOSCH" '(0 0 0) ks "")
(klay "0") (command "_.-INSERT" "AP-BOSCH" '(0 0 0) 1 1 0)
(setq ks (ssadd))
(klay "M-GLASS")
(setq ke (kbox '(30.344997 -52.724995 28.550001) '(30.475001 -38.149998 65.049998)))
(kname ke "LG black InstaView panel")
(ssadd ke ks)
(klay "M-METAL")
(setq ke (kbox '(1.999995 -71.750000 0.000000) '(25.999997 -36.999997 0.600000)))
(kname ke "LG case cap")
(ssadd ke ks)
(klay "M-METAL")
(setq ke (kbox '(1.999995 -71.750000 68.274999) '(25.999997 -36.999997 68.874997)))
(kname ke "LG case cap.001")
(ssadd ke ks)
(klay "M-METAL")
(setq ke (kbox '(2.000013 -71.750000 0.000000) '(2.600002 -36.999997 68.875002)))
(kname ke "LG case rear")
(ssadd ke ks)
(klay "M-METAL")
(setq ke (kbox '(1.999995 -37.000001 0.000000) '(25.999997 -36.500003 68.875002)))
(kname ke "LG case side")
(ssadd ke ks)
(klay "M-METAL")
(setq ke (kbox '(1.999995 -72.249998 0.000000) '(25.999997 -71.749995 68.875002)))
(kname ke "LG case side.001")
(ssadd ke ks)
(klay "M-METAL")
(setq ke (kbox '(3.199991 -69.974997 26.699999) '(3.250003 -38.774997 66.500001)))
(kname ke "LG Cool Guard inset stainless rear")
(ssadd ke ks)
(klay "M-METAL")
(setq ke (kbox '(27.299998 -68.262499 36.350001) '(30.380000 -58.362501 49.600000)))
(kname ke "LG deep sloping dispenser well")
(ssadd ke ks)
(klay "M-METAL")
(setq ke (kbox '(26.230005 -72.139997 23.000001) '(30.329998 -54.484998 23.100001)))
(kname ke "LG dispenser door shell cap")
(ssadd ke ks)
(klay "M-METAL")
(setq ke (kbox '(26.230005 -72.139997 69.699996) '(30.329998 -54.484998 69.800000)))
(kname ke "LG dispenser door shell cap.001")
(ssadd ke ks)
(klay "M-METAL")
(setq ke (kbox '(26.230005 -54.484998 23.050001) '(30.329998 -54.434996 69.750003)))
(kname ke "LG dispenser door shell side")
(ssadd ke ks)
(klay "M-METAL")
(setq ke (kbox '(26.230005 -72.189999 23.050001) '(30.329998 -72.139997 69.750003)))
(kname ke "LG dispenser door shell side.001")
(ssadd ke ks)
(klay "M-METAL")
(setq ke (kbox '(27.230002 -67.162498 36.949999) '(27.330007 -59.462497 49.149999)))
(kname ke "LG dispenser recessed backwall")
(ssadd ke ks)
(klay "M-METAL")
(setq ke (kbox '(30.284999 -68.262499 23.000001) '(30.374997 -58.362496 36.350001)))
(kname ke "LG dispenser stainlessdoor frontskin end")
(ssadd ke ks)
(klay "M-METAL")
(setq ke (kbox '(30.284999 -68.262499 49.600000) '(30.374997 -58.362496 69.799996)))
(kname ke "LG dispenser stainlessdoor frontskin end.001")
(ssadd ke ks)
(klay "M-METAL")
(setq ke (kbox '(30.284999 -58.362496 23.000001) '(30.374997 -54.435001 69.800000)))
(kname ke "LG dispenser stainlessdoor frontskin side")
(ssadd ke ks)
(klay "M-METAL")
(setq ke (kbox '(30.284999 -72.189995 23.000001) '(30.374997 -68.262499 69.800000)))
(kname ke "LG dispenser stainlessdoor frontskin side.001")
(ssadd ke ks)
(klay "M-METAL")
(setq ke (kbox '(30.340004 -68.112497 36.880001) '(30.460002 -58.512498 37.120001)))
(kname ke "LG dispenser thin front drip lip")
(ssadd ke ks)
(klay "M-GLASS")
(setq ke (kbox '(3.500004 -54.224995 49.625002) '(21.499997 -38.074997 49.774999)))
(kname ke "LG fixed split cantilever glass")
(ssadd ke ks)
(klay "M-GLASS")
(setq ke (kbox '(3.500004 -70.674995 49.625002) '(21.499997 -54.524999 49.774999)))
(kname ke "LG fixed split cantilever glass.001")
(ssadd ke ks)
(klay "M-GLASS")
(setq ke (kbox '(3.500004 -54.224995 60.325002) '(21.499997 -38.074997 60.474999)))
(kname ke "LG fixed split cantilever glass.002")
(ssadd ke ks)
(klay "M-METAL")
(setq ke (kbox '(30.380000 -53.745004 28.674999) '(31.979995 -53.245001 29.324999)))
(kname ke "LG flattened handle standoff")
(ssadd ke ks)
(klay "M-METAL")
(setq ke (kbox '(30.380000 -53.745004 63.175001) '(31.979995 -53.245001 63.825001)))
(kname ke "LG flattened handle standoff.001")
(ssadd ke ks)
(klay "M-METAL")
(setq ke (kbox '(30.380000 -55.505002 28.674999) '(31.979995 -55.004999 29.324999)))
(kname ke "LG flattened handle standoff.002")
(ssadd ke ks)
(klay "M-METAL")
(setq ke (kbox '(30.380000 -55.505002 63.175001) '(31.979995 -55.004999 63.825001)))
(kname ke "LG flattened handle standoff.003")
(ssadd ke ks)
(klay "M-METAL")
(setq ke (kbox '(26.225002 -72.124997 1.449999) '(30.375006 -36.624997 22.900001)))
(kname ke "LG freezerfront")
(ssadd ke ks)
(klay "M-METAL")
(setq ke (kbox '(30.439999 -40.174998 21.175001) '(31.840004 -39.574999 21.825001)))
(kname ke "LG freezerhandle mounts")
(ssadd ke ks)
(klay "M-METAL")
(setq ke (kbox '(30.439999 -69.174999 21.175001) '(31.840004 -68.575001 21.825001)))
(kname ke "LG freezerhandle mounts.001")
(ssadd ke ks)
(klay "M-GLASS")
(setq ke (kbox '(3.500004 -70.674995 38.924999) '(21.499997 -38.074997 39.075001)))
(kname ke "LG fullwidth crisper cover glass")
(ssadd ke ks)
(klay "M-METAL")
(setq ke (kbox '(26.230005 -54.264996 23.000001) '(30.329998 -36.609997 23.100001)))
(kname ke "LG InstaView door shell cap")
(ssadd ke ks)
(klay "M-METAL")
(setq ke (kbox '(26.230005 -54.264996 69.699996) '(30.329998 -36.609997 69.800000)))
(kname ke "LG InstaView door shell cap.001")
(ssadd ke ks)
(klay "M-METAL")
(setq ke (kbox '(26.230005 -36.610002 23.050001) '(30.329998 -36.559999 69.750003)))
(kname ke "LG InstaView door shell side")
(ssadd ke ks)
(klay "M-METAL")
(setq ke (kbox '(26.230005 -54.314998 23.050001) '(30.329998 -54.264996 69.750003)))
(kname ke "LG InstaView door shell side.001")
(ssadd ke ks)
(klay "M-METAL")
(setq ke (kbox '(30.284999 -52.724995 23.025000) '(30.374997 -38.149998 28.574999)))
(kname ke "LG InstaView stainlessdoor frontskin end")
(ssadd ke ks)
(klay "M-METAL")
(setq ke (kbox '(30.284999 -52.724995 65.049998) '(30.374997 -38.149998 69.800000)))
(kname ke "LG InstaView stainlessdoor frontskin end.001")
(ssadd ke ks)
(klay "M-METAL")
(setq ke (kbox '(30.284999 -38.152499 23.000001) '(30.374997 -36.562501 69.800000)))
(kname ke "LG InstaView stainlessdoor frontskin side")
(ssadd ke ks)
(klay "M-METAL")
(setq ke (kbox '(30.284999 -54.312501 23.000001) '(30.374997 -52.722503 69.800000)))
(kname ke "LG InstaView stainlessdoor frontskin side.001")
(ssadd ke ks)
(klay "M-METAL")
(setq ke (kbox '(31.480001 -69.374999 20.300000) '(32.750003 -39.374998 22.061601)))
(kname ke "LG sculptedfreezerhandle")
(ssadd ke ks)
(klay "M-METAL")
(setq ke (kbox '(31.725000 -54.195005 27.900000) '(32.750003 -52.795000 64.600002)))
(kname ke "LG sculptedvertical handle")
(ssadd ke ks)
(klay "M-METAL")
(setq ke (kbox '(31.725000 -55.954999 27.900000) '(32.750003 -54.554998 64.600002)))
(kname ke "LG sculptedvertical handle.001")
(ssadd ke ks)
(klay "M-GLASS")
(setq ke (kbox '(12.850002 -70.674995 60.325002) '(21.499997 -54.524999 60.474999)))
(kname ke "LG sliding-half front glass")
(ssadd ke ks)
(klay "M-GLASS")
(setq ke (kbox '(3.500004 -70.674995 60.325002) '(12.699995 -54.524999 60.474999)))
(kname ke "LG sliding-half rear glass")
(ssadd ke ks)
(klay "M-METAL")
(setq ke (kbox '(29.369997 -63.442497 46.950001) '(29.630005 -63.182498 47.350000)))
(kname ke "LG stainless water outlet")
(ssadd ke ks)
(klay "M-METAL")
(setq ke (kbox '(25.950004 -39.375002 69.900000) '(28.450002 -36.975000 70.249997)))
(kname ke "LG visible hinge cover")
(ssadd ke ks)
(klay "M-METAL")
(setq ke (kbox '(25.950004 -71.775001 69.900000) '(28.450002 -69.374999 70.249997)))
(kname ke "LG visible hinge cover.001")
(ssadd ke ks)
(klay "0") (command "_.-BLOCK" "AP-LG" '(0 0 0) ks "")
(klay "0") (command "_.-INSERT" "AP-LG" '(0 0 0) 1 1 0)
(setq ks (ssadd))
(klay "M-METAL")
(setq ke (kbox '(68.499996 -25.999999 35.779999) '(98.499999 -0.000000 36.000002)))
(kname ke "RANGE blackceramic cooktop")
(ssadd ke ks)
(klay "M-METAL")
(setq ke (kbox '(72.110000 -27.940001 31.670001) '(72.490006 -27.660000 32.930001)))
(kname ke "RANGE broad knob grip")
(ssadd ke ks)
(klay "M-METAL")
(setq ke (kbox '(75.809994 -27.940001 31.670001) '(76.189999 -27.660000 32.930001)))
(kname ke "RANGE broad knob grip.001")
(ssadd ke ks)
(klay "M-METAL")
(setq ke (kbox '(90.810000 -27.940001 31.670001) '(91.189996 -27.660000 32.930001)))
(kname ke "RANGE broad knob grip.002")
(ssadd ke ks)
(klay "M-METAL")
(setq ke (kbox '(94.510003 -27.940001 31.670001) '(94.889999 -27.660000 32.930001)))
(kname ke "RANGE broad knob grip.003")
(ssadd ke ks)
(klay "M-METAL")
(setq ke (kbox '(71.471930 -28.500001 26.791046) '(95.528064 -27.140916 27.608954)))
(kname ke "RANGE curved stainless handle")
(ssadd ke ks)
(klay "M-METAL")
(setq ke (kbox '(68.624996 -26.600002 29.300001) '(98.374998 -25.700000 35.300001)))
(kname ke "RANGE frontcontrol stainless fascia")
(ssadd ke ks)
(klay "M-METAL")
(setq ke (kbox '(71.229992 -28.199999 26.930000) '(71.770000 -26.599999 27.470000)))
(kname ke "RANGE handle standoff")
(ssadd ke ks)
(klay "M-METAL")
(setq ke (kbox '(95.229999 -28.199999 26.930000) '(95.769998 -26.599999 27.470000)))
(kname ke "RANGE handle standoff.001")
(ssadd ke ks)
(klay "M-METAL")
(setq ke (kbox '(72.250001 -27.770001 32.709999) '(72.350005 -27.689999 33.189999)))
(kname ke "RANGE knob indicator")
(ssadd ke ks)
(klay "M-METAL")
(setq ke (kbox '(75.949994 -27.770001 32.709999) '(76.049999 -27.689999 33.189999)))
(kname ke "RANGE knob indicator.001")
(ssadd ke ks)
(klay "M-METAL")
(setq ke (kbox '(90.949996 -27.770001 32.709999) '(91.050000 -27.689999 33.189999)))
(kname ke "RANGE knob indicator.002")
(ssadd ke ks)
(klay "M-METAL")
(setq ke (kbox '(94.649999 -27.770001 32.709999) '(94.750003 -27.689999 33.189999)))
(kname ke "RANGE knob indicator.003")
(ssadd ke ks)
(klay "M-METAL")
(setq ke (kbox '(70.524995 -26.400000 4.550000) '(96.474999 -25.099999 5.950000)))
(kname ke "RANGE oven door stainless end")
(ssadd ke ks)
(klay "M-METAL")
(setq ke (kbox '(70.524995 -26.400000 26.750001) '(96.474999 -25.099999 29.049999)))
(kname ke "RANGE oven door stainless end.001")
(ssadd ke ks)
(klay "M-METAL")
(setq ke (kbox '(68.674999 -26.400000 4.549999) '(70.524995 -25.099999 29.049999)))
(kname ke "RANGE oven door stainless side")
(ssadd ke ks)
(klay "M-METAL")
(setq ke (kbox '(96.475004 -26.400000 4.549999) '(98.325001 -25.099999 29.049999)))
(kname ke "RANGE oven door stainless side.001")
(ssadd ke ks)
(klay "M-GLASS")
(setq ke (kbox '(70.550001 -26.479999 6.600000) '(96.449998 -26.380000 26.400000)))
(kname ke "RANGE oven outerglass")
(ssadd ke ks)
(klay "M-METAL")
(setq ke (kbox '(68.799999 -0.400000 0.000000) '(98.199995 -0.000000 35.400001)))
(kname ke "RANGE rearbody")
(ssadd ke ks)
(klay "M-METAL")
(setq ke (kbox '(68.499996 -24.900000 0.000000) '(68.799999 -0.000000 35.400001)))
(kname ke "RANGE stainless side")
(ssadd ke ks)
(klay "M-METAL")
(setq ke (kbox '(98.200000 -24.900000 0.000000) '(98.499999 -0.000000 35.400001)))
(kname ke "RANGE stainless side.001")
(ssadd ke ks)
(klay "M-METAL")
(setq ke (kbox '(68.700000 -26.400000 0.600000) '(98.300000 -25.100000 4.400000)))
(kname ke "Storage drawer front")
(ssadd ke ks)
(klay "M-METAL")
(command "_.CYLINDER" '(75.000000 -8.000000 36.010000) 3 0.025)
(setq ke (entlast))
(kname ke "Electric burner ring")
(ssadd ke ks)
(klay "M-METAL")
(command "_.CYLINDER" '(91.000000 -8.000000 36.010000) 3 0.025)
(setq ke (entlast))
(kname ke "Electric burner ring")
(ssadd ke ks)
(klay "M-METAL")
(command "_.CYLINDER" '(75.000000 -19.000000 36.010000) 4 0.025)
(setq ke (entlast))
(kname ke "Electric burner ring")
(ssadd ke ks)
(klay "M-METAL")
(command "_.CYLINDER" '(91.000000 -19.000000 36.010000) 4 0.025)
(setq ke (entlast))
(kname ke "Electric burner ring")
(ssadd ke ks)
(klay "0") (command "_.-BLOCK" "AP-RANGE" '(0 0 0) ks "")
(klay "0") (command "_.-INSERT" "AP-RANGE" '(0 0 0) 1 1 0)
(setq ks (ssadd))
(klay "M-METAL")
(setq ke (kbox '(141.199999 -140.150006 0.000000) '(162.099999 -117.350000 0.400000)))
(kname ke "WINE FGMIS5060 case cap")
(ssadd ke ks)
(klay "M-METAL")
(setq ke (kbox '(141.199999 -140.150006 33.500000) '(162.099999 -117.350000 33.899999)))
(kname ke "WINE FGMIS5060 case cap.001")
(ssadd ke ks)
(klay "M-METAL")
(setq ke (kbox '(161.800000 -140.450001 0.000000) '(162.100000 -117.050006 33.900001)))
(kname ke "WINE FGMIS5060 case rear")
(ssadd ke ks)
(klay "M-METAL")
(setq ke (kbox '(141.199999 -117.350000 0.000000) '(162.099999 -117.050006 33.900001)))
(kname ke "WINE FGMIS5060 case side")
(ssadd ke ks)
(klay "M-METAL")
(setq ke (kbox '(141.199999 -140.450001 0.000000) '(162.099999 -140.150006 33.900001)))
(kname ke "WINE FGMIS5060 case side.001")
(ssadd ke ks)
(klay "M-METAL")
(setq ke (kbox '(139.600002 -140.450001 0.300000) '(140.200000 -117.050006 3.900000)))
(kname ke "WINE frontvent stainless")
(ssadd ke ks)
(klay "M-METAL")
(setq ke (kbox '(138.250001 -119.849997 8.750000) '(139.550002 -119.349994 9.250000)))
(kname ke "WINE handle mount")
(ssadd ke ks)
(klay "M-METAL")
(setq ke (kbox '(138.250001 -119.849997 27.750001) '(139.550002 -119.349994 28.249999)))
(kname ke "WINE handle mount.001")
(ssadd ke ks)
(klay "M-METAL")
(setq ke (kbox '(137.719578 -119.999994 8.077937) '(138.849783 -119.199997 28.122063)))
(kname ke "WINE photo curvedhandle")
(ssadd ke ks)
(klay "M-METAL")
(setq ke (kbox '(139.599999 -140.450001 4.000000) '(140.700001 -117.050006 5.100000)))
(kname ke "WINE stainless doorframe horizontal")
(ssadd ke ks)
(klay "M-METAL")
(setq ke (kbox '(139.599999 -140.450001 32.299999) '(140.700001 -117.050006 33.400000)))
(kname ke "WINE stainless doorframe horizontal.001")
(ssadd ke ks)
(klay "M-METAL")
(setq ke (kbox '(139.599999 -118.149998 4.000000) '(140.700001 -117.050006 33.400000)))
(kname ke "WINE stainless doorframe vertical")
(ssadd ke ks)
(klay "M-METAL")
(setq ke (kbox '(139.599999 -140.449991 4.000000) '(140.700001 -139.349999 33.400000)))
(kname ke "WINE stainless doorframe vertical.001")
(ssadd ke ks)
(klay "M-GLASS")
(setq ke (kbox '(139.650000 -140.350000 4.000000) '(140.000000 -117.100000 33.700000)))
(kname ke "Wine glass door")
(ssadd ke ks)
(klay "C-CARCASS")
(setq ke (kbox '(140.000000 -139.900000 6.000000) '(163.000000 -117.800000 6.400000)))
(kname ke "Wine shelf")
(ssadd ke ks)
(klay "C-CARCASS")
(setq ke (kbox '(140.000000 -139.900000 11.000000) '(163.000000 -117.800000 11.400000)))
(kname ke "Wine shelf")
(ssadd ke ks)
(klay "C-CARCASS")
(setq ke (kbox '(140.000000 -139.900000 16.000000) '(163.000000 -117.800000 16.400000)))
(kname ke "Wine shelf")
(ssadd ke ks)
(klay "C-CARCASS")
(setq ke (kbox '(140.000000 -139.900000 21.000000) '(163.000000 -117.800000 21.400000)))
(kname ke "Wine shelf")
(ssadd ke ks)
(klay "C-CARCASS")
(setq ke (kbox '(140.000000 -139.900000 26.000000) '(163.000000 -117.800000 26.400000)))
(kname ke "Wine shelf")
(ssadd ke ks)
(klay "C-CARCASS")
(setq ke (kbox '(140.000000 -139.900000 31.000000) '(163.000000 -117.800000 31.400000)))
(kname ke "Wine shelf")
(ssadd ke ks)
(klay "0") (command "_.-BLOCK" "AP-WINE" '(0 0 0) ks "")
(klay "0") (command "_.-INSERT" "AP-WINE" '(0 0 0) 1 1 0)
(setq ks (ssadd))
(klay "M-METAL")
(setq ke (kbox '(142.000000 -74.250000 25.480000) '(161.000000 -44.250000 35.500000)))
(setq kc (kbox '(142.08 -74.17 25.56) '(160.92 -44.33 36)))
(command "_.SUBTRACT" ke "" kc "")
(kname ke "Sink outer")
(ssadd ke ks)
(klay "0") (command "_.-BLOCK" "SINK-KWU110-30-STUDY" '(0 0 0) ks "")
(klay "0") (command "_.-INSERT" "SINK-KWU110-30-STUDY" '(0 0 0) 1 1 0)
(setq ks (ssadd))
(klay "M-METAL")
(command "_.CYLINDER" '(162.250000 -59.250000 36.000000) 1.0625 0.2)
(setq ke (entlast))
(kname ke "KPF1610 deck base")
(ssadd ke ks)
(klay "M-METAL")
(command "_.CYLINDER" '(162.250000 -59.250000 36.200000) 0.65 6.55)
(setq ke (entlast))
(kname ke "KPF1610 mixer body")
(ssadd ke ks)
(klay "M-METAL")
(command "_.CYLINDER" '(162.250000 -59.250000 42.750000) 0.23 7.337499999999999)
(setq ke (entlast))
(kname ke "KPF1610 riser")
(ssadd ke ks)
(klay "M-METAL")
(setq kp (entmakex (list '(0 . "ARC") (cons 10 '(157.937500 50.087500 59.250000)) (cons 40 4.3125) '(50 . 0.0) '(51 . 3.141592653589793) '(210 0 -1 0))))
(command "_.CIRCLE" '(162.250000 -59.250000 50.087500) 0.23)
(setq kpr (entlast))
(command "_.SWEEP" kpr "" kp)
(setq ke (entlast))
(if (entget kp) (entdel kp))
(kname ke "KPF1610 curved hose")
(ssadd ke ks)
(klay "M-METAL")
(command "_.CYLINDER" '(153.625000 -59.250000 46.600000) 0.23 3.487499999999997)
(setq ke (entlast))
(kname ke "KPF1610 hose to sprayhead")
(ssadd ke ks)
(klay "M-METAL")
(command "_.CYLINDER" '(153.625000 -59.250000 42.250000) 0.8 4.35)
(setq ke (entlast))
(kname ke "KPF1610 sprayhead")
(ssadd ke ks)
(klay "M-METAL")
(command "_.CYLINDER" '(153.625000 -59.250000 42.250000) 0.83 0.12)
(setq ke (entlast))
(kname ke "KPF1610 outlet ring")
(ssadd ke ks)
(klay "M-METAL")
(command "_.CYLINDER" '(154.425000 -59.250000 44.600000) 0.18 7.825)
(setq ke (entlast))
(command "_.ROTATE3D" ke "" "_Y" '(154.425000 -59.250000 44.600000) 90)
(kname ke "KPF1610 support arm")
(ssadd ke ks)
(klay "M-METAL")
(command "_.CYLINDER" '(162.250000 -60.900000 39.250000) 0.13 3.3)
(setq ke (entlast))
(kname ke "KPF1610 side lever")
(ssadd ke ks)
(klay "M-METAL")
(setq ke (kbox '(161.900000 -61.050000 38.700000) '(162.600000 -59.650000 39.500000)))
(kname ke "KPF1610 lever hub")
(ssadd ke ks)
(klay "M-METAL")
(command "_.TORUS" '(162.250000 -59.250000 50.087500) 0.3 0.05)
(setq ke (entlast))
(kname ke "KPF1610 spring wrap")
(ssadd ke ks)
(klay "M-METAL")
(command "_.TORUS" '(162.218557 -59.250000 50.607314) 0.3 0.05)
(setq ke (entlast))
(command "_.ROTATE3D" ke "" "_Y" '(162.218557 -59.250000 50.607314) -6.923076923076923)
(kname ke "KPF1610 spring wrap")
(ssadd ke ks)
(klay "M-METAL")
(command "_.TORUS" '(162.124687 -59.250000 51.119549) 0.3 0.05)
(setq ke (entlast))
(command "_.ROTATE3D" ke "" "_Y" '(162.124687 -59.250000 51.119549) -13.846153846153847)
(kname ke "KPF1610 spring wrap")
(ssadd ke ks)
(klay "M-METAL")
(command "_.TORUS" '(161.969758 -59.250000 51.616734) 0.3 0.05)
(setq ke (entlast))
(command "_.ROTATE3D" ke "" "_Y" '(161.969758 -59.250000 51.616734) -20.76923076923077)
(kname ke "KPF1610 spring wrap")
(ssadd ke ks)
(klay "M-METAL")
(command "_.TORUS" '(161.756029 -59.250000 52.091619) 0.3 0.05)
(setq ke (entlast))
(command "_.ROTATE3D" ke "" "_Y" '(161.756029 -59.250000 52.091619) -27.692307692307693)
(kname ke "KPF1610 spring wrap")
(ssadd ke ks)
(klay "M-METAL")
(command "_.TORUS" '(161.486618 -59.250000 52.537279) 0.3 0.05)
(setq ke (entlast))
(command "_.ROTATE3D" ke "" "_Y" '(161.486618 -59.250000 52.537279) -34.61538461538461)
(kname ke "KPF1610 spring wrap")
(ssadd ke ks)
(klay "M-METAL")
(command "_.TORUS" '(161.165453 -59.250000 52.947216) 0.3 0.05)
(setq ke (entlast))
(command "_.ROTATE3D" ke "" "_Y" '(161.165453 -59.250000 52.947216) -41.53846153846154)
(kname ke "KPF1610 spring wrap")
(ssadd ke ks)
(klay "M-METAL")
(command "_.TORUS" '(160.797216 -59.250000 53.315453) 0.3 0.05)
(setq ke (entlast))
(command "_.ROTATE3D" ke "" "_Y" '(160.797216 -59.250000 53.315453) -48.46153846153846)
(kname ke "KPF1610 spring wrap")
(ssadd ke ks)
(klay "M-METAL")
(command "_.TORUS" '(160.387279 -59.250000 53.636618) 0.3 0.05)
(setq ke (entlast))
(command "_.ROTATE3D" ke "" "_Y" '(160.387279 -59.250000 53.636618) -55.38461538461539)
(kname ke "KPF1610 spring wrap")
(ssadd ke ks)
(klay "M-METAL")
(command "_.TORUS" '(159.941619 -59.250000 53.906029) 0.3 0.05)
(setq ke (entlast))
(command "_.ROTATE3D" ke "" "_Y" '(159.941619 -59.250000 53.906029) -62.30769230769231)
(kname ke "KPF1610 spring wrap")
(ssadd ke ks)
(klay "M-METAL")
(command "_.TORUS" '(159.466734 -59.250000 54.119758) 0.3 0.05)
(setq ke (entlast))
(command "_.ROTATE3D" ke "" "_Y" '(159.466734 -59.250000 54.119758) -69.23076923076923)
(kname ke "KPF1610 spring wrap")
(ssadd ke ks)
(klay "M-METAL")
(command "_.TORUS" '(158.969549 -59.250000 54.274687) 0.3 0.05)
(setq ke (entlast))
(command "_.ROTATE3D" ke "" "_Y" '(158.969549 -59.250000 54.274687) -76.15384615384616)
(kname ke "KPF1610 spring wrap")
(ssadd ke ks)
(klay "M-METAL")
(command "_.TORUS" '(158.457314 -59.250000 54.368557) 0.3 0.05)
(setq ke (entlast))
(command "_.ROTATE3D" ke "" "_Y" '(158.457314 -59.250000 54.368557) -83.07692307692308)
(kname ke "KPF1610 spring wrap")
(ssadd ke ks)
(klay "M-METAL")
(command "_.TORUS" '(157.937500 -59.250000 54.400000) 0.3 0.05)
(setq ke (entlast))
(command "_.ROTATE3D" ke "" "_Y" '(157.937500 -59.250000 54.400000) -90.0)
(kname ke "KPF1610 spring wrap")
(ssadd ke ks)
(klay "M-METAL")
(command "_.TORUS" '(157.417686 -59.250000 54.368557) 0.3 0.05)
(setq ke (entlast))
(command "_.ROTATE3D" ke "" "_Y" '(157.417686 -59.250000 54.368557) -96.92307692307692)
(kname ke "KPF1610 spring wrap")
(ssadd ke ks)
(klay "M-METAL")
(command "_.TORUS" '(156.905451 -59.250000 54.274687) 0.3 0.05)
(setq ke (entlast))
(command "_.ROTATE3D" ke "" "_Y" '(156.905451 -59.250000 54.274687) -103.84615384615384)
(kname ke "KPF1610 spring wrap")
(ssadd ke ks)
(klay "M-METAL")
(command "_.TORUS" '(156.408266 -59.250000 54.119758) 0.3 0.05)
(setq ke (entlast))
(command "_.ROTATE3D" ke "" "_Y" '(156.408266 -59.250000 54.119758) -110.76923076923077)
(kname ke "KPF1610 spring wrap")
(ssadd ke ks)
(klay "M-METAL")
(command "_.TORUS" '(155.933381 -59.250000 53.906029) 0.3 0.05)
(setq ke (entlast))
(command "_.ROTATE3D" ke "" "_Y" '(155.933381 -59.250000 53.906029) -117.6923076923077)
(kname ke "KPF1610 spring wrap")
(ssadd ke ks)
(klay "M-METAL")
(command "_.TORUS" '(155.487721 -59.250000 53.636618) 0.3 0.05)
(setq ke (entlast))
(command "_.ROTATE3D" ke "" "_Y" '(155.487721 -59.250000 53.636618) -124.61538461538461)
(kname ke "KPF1610 spring wrap")
(ssadd ke ks)
(klay "M-METAL")
(command "_.TORUS" '(155.077784 -59.250000 53.315453) 0.3 0.05)
(setq ke (entlast))
(command "_.ROTATE3D" ke "" "_Y" '(155.077784 -59.250000 53.315453) -131.53846153846155)
(kname ke "KPF1610 spring wrap")
(ssadd ke ks)
(klay "M-METAL")
(command "_.TORUS" '(154.709547 -59.250000 52.947216) 0.3 0.05)
(setq ke (entlast))
(command "_.ROTATE3D" ke "" "_Y" '(154.709547 -59.250000 52.947216) -138.46153846153845)
(kname ke "KPF1610 spring wrap")
(ssadd ke ks)
(klay "M-METAL")
(command "_.TORUS" '(154.388382 -59.250000 52.537279) 0.3 0.05)
(setq ke (entlast))
(command "_.ROTATE3D" ke "" "_Y" '(154.388382 -59.250000 52.537279) -145.3846153846154)
(kname ke "KPF1610 spring wrap")
(ssadd ke ks)
(klay "M-METAL")
(command "_.TORUS" '(154.118971 -59.250000 52.091619) 0.3 0.05)
(setq ke (entlast))
(command "_.ROTATE3D" ke "" "_Y" '(154.118971 -59.250000 52.091619) -152.30769230769232)
(kname ke "KPF1610 spring wrap")
(ssadd ke ks)
(klay "M-METAL")
(command "_.TORUS" '(153.905242 -59.250000 51.616734) 0.3 0.05)
(setq ke (entlast))
(command "_.ROTATE3D" ke "" "_Y" '(153.905242 -59.250000 51.616734) -159.23076923076923)
(kname ke "KPF1610 spring wrap")
(ssadd ke ks)
(klay "M-METAL")
(command "_.TORUS" '(153.750313 -59.250000 51.119549) 0.3 0.05)
(setq ke (entlast))
(command "_.ROTATE3D" ke "" "_Y" '(153.750313 -59.250000 51.119549) -166.15384615384616)
(kname ke "KPF1610 spring wrap")
(ssadd ke ks)
(klay "M-METAL")
(command "_.TORUS" '(153.656443 -59.250000 50.607314) 0.3 0.05)
(setq ke (entlast))
(command "_.ROTATE3D" ke "" "_Y" '(153.656443 -59.250000 50.607314) -173.07692307692307)
(kname ke "KPF1610 spring wrap")
(ssadd ke ks)
(klay "M-METAL")
(command "_.TORUS" '(153.625000 -59.250000 50.087500) 0.3 0.05)
(setq ke (entlast))
(command "_.ROTATE3D" ke "" "_Y" '(153.625000 -59.250000 50.087500) -180.0)
(kname ke "KPF1610 spring wrap")
(ssadd ke ks)
(klay "M-METAL")
(command "_.TORUS" '(162.250000 -59.250000 43.250000) 0.3 0.05)
(setq ke (entlast))
(kname ke "KPF1610 riser wrap")
(ssadd ke ks)
(klay "M-METAL")
(command "_.TORUS" '(162.250000 -59.250000 44.000000) 0.3 0.05)
(setq ke (entlast))
(kname ke "KPF1610 riser wrap")
(ssadd ke ks)
(klay "M-METAL")
(command "_.TORUS" '(162.250000 -59.250000 44.750000) 0.3 0.05)
(setq ke (entlast))
(kname ke "KPF1610 riser wrap")
(ssadd ke ks)
(klay "M-METAL")
(command "_.TORUS" '(162.250000 -59.250000 45.500000) 0.3 0.05)
(setq ke (entlast))
(kname ke "KPF1610 riser wrap")
(ssadd ke ks)
(klay "M-METAL")
(command "_.TORUS" '(162.250000 -59.250000 46.250000) 0.3 0.05)
(setq ke (entlast))
(kname ke "KPF1610 riser wrap")
(ssadd ke ks)
(klay "M-METAL")
(command "_.TORUS" '(162.250000 -59.250000 47.000000) 0.3 0.05)
(setq ke (entlast))
(kname ke "KPF1610 riser wrap")
(ssadd ke ks)
(klay "M-METAL")
(command "_.TORUS" '(162.250000 -59.250000 47.750000) 0.3 0.05)
(setq ke (entlast))
(kname ke "KPF1610 riser wrap")
(ssadd ke ks)
(klay "M-METAL")
(command "_.TORUS" '(162.250000 -59.250000 48.500000) 0.3 0.05)
(setq ke (entlast))
(kname ke "KPF1610 riser wrap")
(ssadd ke ks)
(klay "M-METAL")
(command "_.TORUS" '(162.250000 -59.250000 49.250000) 0.3 0.05)
(setq ke (entlast))
(kname ke "KPF1610 riser wrap")
(ssadd ke ks)
(klay "M-METAL")
(command "_.CYLINDER" '(161.200000 -78.250000 36.000000) 0.7 0.3)
(setq ke (entlast))
(kname ke "Filter deck base")
(ssadd ke ks)
(klay "M-METAL")
(command "_.CYLINDER" '(161.200000 -78.250000 36.300000) 0.16 8.540000000000006)
(setq ke (entlast))
(kname ke "Filter riser")
(ssadd ke ks)
(klay "M-METAL")
(setq kp (entmakex (list '(0 . "ARC") (cons 10 '(158.200000 44.840000 78.250000)) (cons 40 3) '(50 . 0.0) '(51 . 3.141592653589793) '(210 0 -1 0))))
(command "_.CIRCLE" '(161.200000 -78.250000 44.840000) 0.16)
(setq kpr (entlast))
(command "_.SWEEP" kpr "" kp)
(setq ke (entlast))
(if (entget kp) (entdel kp))
(kname ke "Filter gooseneck")
(ssadd ke ks)
(klay "M-METAL")
(command "_.CYLINDER" '(155.200000 -78.250000 43.040000) 0.16 1.8)
(setq ke (entlast))
(kname ke "Filter outlet")
(ssadd ke ks)
(klay "M-METAL")
(command "_.CYLINDER" '(161.200000 -79.450000 36.700000) 0.1 2.2)
(setq ke (entlast))
(kname ke "Filter lever")
(ssadd ke ks)
(klay "0") (command "_.-BLOCK" "TAPS-STUDY" '(0 0 0) ks "")
(klay "0") (command "_.-INSERT" "TAPS-STUDY" '(0 0 0) 1 1 0)
(setq ks (ssadd))
(klay "A-JOINERY")
(setq ke (kbox '(22.375000 -192.250000 0.375000) '(24.125000 -156.250000 80.375000)))
(kname ke "Pocket leaf")
(ssadd ke ks)
(klay "A-JOINERY")
(setq ke (kbox '(24.125000 -188.250000 5.000000) '(24.375000 -160.250000 24.000000)))
(kname ke "Raised door panel")
(ssadd ke ks)
(klay "A-JOINERY")
(setq ke (kbox '(24.125000 -188.250000 28.000000) '(24.375000 -160.250000 48.000000)))
(kname ke "Raised door panel")
(ssadd ke ks)
(klay "A-JOINERY")
(setq ke (kbox '(24.125000 -188.250000 52.000000) '(24.375000 -160.250000 75.000000)))
(kname ke "Raised door panel")
(ssadd ke ks)
(klay "C-HARDWARE")
(setq ke (kbox '(24.150000 -189.650000 34.800000) '(24.300000 -188.350000 38.200000)))
(kname ke "Recessed pull")
(ssadd ke ks)
(klay "0") (command "_.-BLOCK" "GARAGE-POCKET-DOOR" '(0 0 0) ks "")
(klay "0") (command "_.-INSERT" "GARAGE-POCKET-DOOR" '(0 0 0) 1 1 0)
(setq ks (ssadd))
(klay "M-METAL")
(command "_.TORUS" '(156.250000 -49.250000 25.600000) 1.75 0.07)
(setq ke (entlast))
(kname ke "Sink drain rim study")
(ssadd ke ks)
(klay "M-GLASS")
(command "_.CYLINDER" '(156.250000 -49.250000 25.560000) 1.25 0.025)
(setq ke (entlast))
(kname ke "Sink drain dark well")
(ssadd ke ks)
(klay "M-METAL")
(command "_.TORUS" '(156.250000 -49.250000 25.610000) 0.3 0.025)
(setq ke (entlast))
(kname ke "Sink strainer study")
(ssadd ke ks)
(klay "M-METAL")
(command "_.TORUS" '(156.250000 -49.250000 25.610000) 0.7 0.025)
(setq ke (entlast))
(kname ke "Sink strainer study")
(ssadd ke ks)
(klay "M-METAL")
(command "_.TORUS" '(156.250000 -49.250000 25.610000) 1.1 0.025)
(setq ke (entlast))
(kname ke "Sink strainer study")
(ssadd ke ks)
(klay "0") (command "_.-BLOCK" "SINK-DRAIN-STUDY" '(0 0 0) ks "")
(klay "0") (command "_.-INSERT" "SINK-DRAIN-STUDY" '(0 0 0) 1 1 0)
(setq ks (ssadd))
(klay "E-LIGHT")
(command "_.TORUS" '(35.000000 -43.000000 107.970000) 1.2 0.09)
(setq ke (entlast))
(kname ke "Recessed trim study")
(ssadd ke ks)
(klay "E-LIGHT")
(command "_.CYLINDER" '(35.000000 -43.000000 108.020000) 1.06 0.63)
(setq ke (entlast))
(kname ke "Recessed reflector study")
(ssadd ke ks)
(klay "E-LIGHT")
(command "_.CYLINDER" '(35.000000 -43.000000 108.640000) 0.65 0.05)
(setq ke (entlast))
(kname ke "Recessed lens study")
(ssadd ke ks)
(klay "0") (command "_.-BLOCK" "CEILING-LIGHT-1" '(0 0 0) ks "")
(klay "A-CEILING") (command "_.-INSERT" "CEILING-LIGHT-1" '(0 0 0) 1 1 0)
(setq ks (ssadd))
(klay "E-LIGHT")
(command "_.TORUS" '(130.000000 -43.000000 107.970000) 1.2 0.09)
(setq ke (entlast))
(kname ke "Recessed trim study")
(ssadd ke ks)
(klay "E-LIGHT")
(command "_.CYLINDER" '(130.000000 -43.000000 108.020000) 1.06 0.63)
(setq ke (entlast))
(kname ke "Recessed reflector study")
(ssadd ke ks)
(klay "E-LIGHT")
(command "_.CYLINDER" '(130.000000 -43.000000 108.640000) 0.65 0.05)
(setq ke (entlast))
(kname ke "Recessed lens study")
(ssadd ke ks)
(klay "0") (command "_.-BLOCK" "CEILING-LIGHT-2" '(0 0 0) ks "")
(klay "A-CEILING") (command "_.-INSERT" "CEILING-LIGHT-2" '(0 0 0) 1 1 0)
(setq ks (ssadd))
(klay "E-LIGHT")
(command "_.TORUS" '(45.000000 -95.000000 107.970000) 1.2 0.09)
(setq ke (entlast))
(kname ke "Recessed trim study")
(ssadd ke ks)
(klay "E-LIGHT")
(command "_.CYLINDER" '(45.000000 -95.000000 108.020000) 1.06 0.63)
(setq ke (entlast))
(kname ke "Recessed reflector study")
(ssadd ke ks)
(klay "E-LIGHT")
(command "_.CYLINDER" '(45.000000 -95.000000 108.640000) 0.65 0.05)
(setq ke (entlast))
(kname ke "Recessed lens study")
(ssadd ke ks)
(klay "0") (command "_.-BLOCK" "CEILING-LIGHT-3" '(0 0 0) ks "")
(klay "A-CEILING") (command "_.-INSERT" "CEILING-LIGHT-3" '(0 0 0) 1 1 0)
(setq ks (ssadd))
(klay "E-LIGHT")
(command "_.TORUS" '(125.000000 -110.000000 107.970000) 1.2 0.09)
(setq ke (entlast))
(kname ke "Recessed trim study")
(ssadd ke ks)
(klay "E-LIGHT")
(command "_.CYLINDER" '(125.000000 -110.000000 108.020000) 1.06 0.63)
(setq ke (entlast))
(kname ke "Recessed reflector study")
(ssadd ke ks)
(klay "E-LIGHT")
(command "_.CYLINDER" '(125.000000 -110.000000 108.640000) 0.65 0.05)
(setq ke (entlast))
(kname ke "Recessed lens study")
(ssadd ke ks)
(klay "0") (command "_.-BLOCK" "CEILING-LIGHT-4" '(0 0 0) ks "")
(klay "A-CEILING") (command "_.-INSERT" "CEILING-LIGHT-4" '(0 0 0) 1 1 0)
(setq ks (ssadd))
(klay "E-LIGHT")
(command "_.TORUS" '(45.000000 -160.000000 107.970000) 1.2 0.09)
(setq ke (entlast))
(kname ke "Recessed trim study")
(ssadd ke ks)
(klay "E-LIGHT")
(command "_.CYLINDER" '(45.000000 -160.000000 108.020000) 1.06 0.63)
(setq ke (entlast))
(kname ke "Recessed reflector study")
(ssadd ke ks)
(klay "E-LIGHT")
(command "_.CYLINDER" '(45.000000 -160.000000 108.640000) 0.65 0.05)
(setq ke (entlast))
(kname ke "Recessed lens study")
(ssadd ke ks)
(klay "0") (command "_.-BLOCK" "CEILING-LIGHT-5" '(0 0 0) ks "")
(klay "A-CEILING") (command "_.-INSERT" "CEILING-LIGHT-5" '(0 0 0) 1 1 0)
(setq ks (ssadd))
(klay "E-LIGHT")
(command "_.TORUS" '(128.000000 -166.000000 107.970000) 1.2 0.09)
(setq ke (entlast))
(kname ke "Recessed trim study")
(ssadd ke ks)
(klay "E-LIGHT")
(command "_.CYLINDER" '(128.000000 -166.000000 108.020000) 1.06 0.63)
(setq ke (entlast))
(kname ke "Recessed reflector study")
(ssadd ke ks)
(klay "E-LIGHT")
(command "_.CYLINDER" '(128.000000 -166.000000 108.640000) 0.65 0.05)
(setq ke (entlast))
(kname ke "Recessed lens study")
(ssadd ke ks)
(klay "0") (command "_.-BLOCK" "CEILING-LIGHT-6" '(0 0 0) ks "")
(klay "A-CEILING") (command "_.-INSERT" "CEILING-LIGHT-6" '(0 0 0) 1 1 0)
(setq ks (ssadd))
(klay "E-LIGHT")
(setq ke (kbox '(0.500004 -13.720000 55.749998) '(50.000000 -13.580000 55.850003)))
(kname ke "Range undercabinet diffuser")
(ssadd ke ks)
(klay "E-LIGHT")
(setq ke (kbox '(116.999999 -13.720000 55.749998) '(164.500002 -13.580000 55.850003)))
(kname ke "Range undercabinet diffuser.001")
(ssadd ke ks)
(klay "E-LIGHT")
(setq ke (kbox '(151.280006 -31.750000 55.749998) '(151.420006 -16.749999 55.850003)))
(kname ke "Sink undercabinet diffuser")
(ssadd ke ks)
(klay "E-LIGHT")
(setq ke (kbox '(151.280006 -163.000005 55.749998) '(151.420006 -86.749999 55.850003)))
(kname ke "Sink undercabinet diffuser.001")
(ssadd ke ks)
(klay "0") (command "_.-BLOCK" "UNDERCABINET-LIGHTING" '(0 0 0) ks "")
(klay "0") (command "_.-INSERT" "UNDERCABINET-LIGHTING" '(0 0 0) 1 1 0)
(setq ks (ssadd))
(klay "F-CONTEXT")
(command "_.CYLINDER" '(70.650000 -81.000000 23.900000) 6.75 1.1)
(setq ke (entlast))
(kname ke "Compact stool seat")
(ssadd ke ks)
(klay "F-CONTEXT")
(setq ke (kbox '(64.950000 -76.100000 0.400000) '(65.750000 -75.300000 23.900000)))
(kname ke "Stool leg")
(ssadd ke ks)
(klay "F-CONTEXT")
(setq ke (kbox '(64.950000 -86.700000 0.400000) '(65.750000 -85.900000 23.900000)))
(kname ke "Stool leg")
(ssadd ke ks)
(klay "F-CONTEXT")
(setq ke (kbox '(75.550000 -76.100000 0.400000) '(76.350000 -75.300000 23.900000)))
(kname ke "Stool leg")
(ssadd ke ks)
(klay "F-CONTEXT")
(setq ke (kbox '(75.550000 -86.700000 0.400000) '(76.350000 -85.900000 23.900000)))
(kname ke "Stool leg")
(ssadd ke ks)
(klay "F-CONTEXT")
(setq ke (kbox '(65.350000 -75.950000 8.250000) '(75.950000 -75.450000 8.750000)))
(kname ke "Stool footrest")
(ssadd ke ks)
(klay "F-CONTEXT")
(setq ke (kbox '(65.350000 -86.550000 8.250000) '(75.950000 -86.050000 8.750000)))
(kname ke "Stool footrest")
(ssadd ke ks)
(klay "F-CONTEXT")
(setq ke (kbox '(65.100000 -86.300000 10.000000) '(65.600000 -75.700000 10.500000)))
(kname ke "Stool stretcher")
(ssadd ke ks)
(klay "F-CONTEXT")
(setq ke (kbox '(75.700000 -86.300000 10.000000) '(76.200000 -75.700000 10.500000)))
(kname ke "Stool stretcher")
(ssadd ke ks)
(klay "0") (command "_.-BLOCK" "STOOL-CONTEXT-1" '(0 0 0) ks "")
(klay "0") (command "_.-INSERT" "STOOL-CONTEXT-1" '(0 0 0) 1 1 0)
(setq ks (ssadd))
(klay "F-CONTEXT")
(command "_.CYLINDER" '(70.650000 -105.000000 23.900000) 6.75 1.1)
(setq ke (entlast))
(kname ke "Compact stool seat")
(ssadd ke ks)
(klay "F-CONTEXT")
(setq ke (kbox '(64.950000 -100.100000 0.400000) '(65.750000 -99.300000 23.900000)))
(kname ke "Stool leg")
(ssadd ke ks)
(klay "F-CONTEXT")
(setq ke (kbox '(64.950000 -110.700000 0.400000) '(65.750000 -109.900000 23.900000)))
(kname ke "Stool leg")
(ssadd ke ks)
(klay "F-CONTEXT")
(setq ke (kbox '(75.550000 -100.100000 0.400000) '(76.350000 -99.300000 23.900000)))
(kname ke "Stool leg")
(ssadd ke ks)
(klay "F-CONTEXT")
(setq ke (kbox '(75.550000 -110.700000 0.400000) '(76.350000 -109.900000 23.900000)))
(kname ke "Stool leg")
(ssadd ke ks)
(klay "F-CONTEXT")
(setq ke (kbox '(65.350000 -99.950000 8.250000) '(75.950000 -99.450000 8.750000)))
(kname ke "Stool footrest")
(ssadd ke ks)
(klay "F-CONTEXT")
(setq ke (kbox '(65.350000 -110.550000 8.250000) '(75.950000 -110.050000 8.750000)))
(kname ke "Stool footrest")
(ssadd ke ks)
(klay "F-CONTEXT")
(setq ke (kbox '(65.100000 -110.300000 10.000000) '(65.600000 -99.700000 10.500000)))
(kname ke "Stool stretcher")
(ssadd ke ks)
(klay "F-CONTEXT")
(setq ke (kbox '(75.700000 -110.300000 10.000000) '(76.200000 -99.700000 10.500000)))
(kname ke "Stool stretcher")
(ssadd ke ks)
(klay "0") (command "_.-BLOCK" "STOOL-CONTEXT-2" '(0 0 0) ks "")
(klay "0") (command "_.-INSERT" "STOOL-CONTEXT-2" '(0 0 0) 1 1 0)
(setq ks (ssadd))
(klay "F-CONTEXT")
(command "_.CYLINDER" '(70.650000 -129.000000 23.900000) 6.75 1.1)
(setq ke (entlast))
(kname ke "Compact stool seat")
(ssadd ke ks)
(klay "F-CONTEXT")
(setq ke (kbox '(64.950000 -124.100000 0.400000) '(65.750000 -123.300000 23.900000)))
(kname ke "Stool leg")
(ssadd ke ks)
(klay "F-CONTEXT")
(setq ke (kbox '(64.950000 -134.700000 0.400000) '(65.750000 -133.900000 23.900000)))
(kname ke "Stool leg")
(ssadd ke ks)
(klay "F-CONTEXT")
(setq ke (kbox '(75.550000 -124.100000 0.400000) '(76.350000 -123.300000 23.900000)))
(kname ke "Stool leg")
(ssadd ke ks)
(klay "F-CONTEXT")
(setq ke (kbox '(75.550000 -134.700000 0.400000) '(76.350000 -133.900000 23.900000)))
(kname ke "Stool leg")
(ssadd ke ks)
(klay "F-CONTEXT")
(setq ke (kbox '(65.350000 -123.950000 8.250000) '(75.950000 -123.450000 8.750000)))
(kname ke "Stool footrest")
(ssadd ke ks)
(klay "F-CONTEXT")
(setq ke (kbox '(65.350000 -134.550000 8.250000) '(75.950000 -134.050000 8.750000)))
(kname ke "Stool footrest")
(ssadd ke ks)
(klay "F-CONTEXT")
(setq ke (kbox '(65.100000 -134.300000 10.000000) '(65.600000 -123.700000 10.500000)))
(kname ke "Stool stretcher")
(ssadd ke ks)
(klay "F-CONTEXT")
(setq ke (kbox '(75.700000 -134.300000 10.000000) '(76.200000 -123.700000 10.500000)))
(kname ke "Stool stretcher")
(ssadd ke ks)
(klay "0") (command "_.-BLOCK" "STOOL-CONTEXT-3" '(0 0 0) ks "")
(klay "0") (command "_.-INSERT" "STOOL-CONTEXT-3" '(0 0 0) 1 1 0)
(command "_.-LAYER" "_F" "A-WALL,A-CEILING" "")
(command "_.VPOINT" '(0.6 -3 2))
(command "_.ZOOM" "_E")
(command "_.VSCURRENT" "_Conceptual")
(command "_.-VIEW" "_D" "Kitchen_Interior_Axonometric")
(command "_.-VIEW" "_S" "Kitchen_Interior_Axonometric")
(command "_.QSAVE")
(princ "\nKITCHEN_MODEL_COMPLETE\n") (princ)
